Attribute VB_Name = "compute_area"
Public Sub CA()
    Dim objAcadEntity As AcadEntity
    Dim LwpLine1 As AcadLWPolyline
    Dim LwpLine2 As AcadLWPolyline
    Dim objCircle As AcadCircle
    Dim objText As AcadText
    Dim lwArea, sumX, sumY, total As Double
    Dim areaArray() As Variant
    Dim pointListX() As Variant
    Dim pointListY() As Variant
    Dim varP0 As Variant
    Dim textPoint(0 To 2) As Double
    Dim tablePoint(0 To 7) As Double
    Dim arraySize, counter As Integer

    On Error GoTo Z
    Call CreateLayer("AREATEXT", 6, "CONTINUOUS")
    arraySize = -1
    counter = 1
    total = 0
    Do While Err.Number = 0
        ThisDrawing.Utility.GetEntity objAcadEntity, varPickPoint, "請選擇多邊形"
        If TypeOf objAcadEntity Is AcadLWPolyline Then
            arraySize = arraySize + 2
            ReDim Preserve areaArray(arraySize)
            Set LwpLine1 = objAcadEntity
            lwArea = Round(LwpLine1.Area / 10000, 2)
            
            '----------多邊形中心點----------
            ReDim pointListX((UBound(LwpLine1.Coordinates) - 1) / 2)
            ReDim pointListY((UBound(LwpLine1.Coordinates) - 1) / 2)
            For Index = 0 To (UBound(LwpLine1.Coordinates) - 1) / 2
                pointListX(Index) = LwpLine1.Coordinates(Index * 2)
            Next
            
            For Index = 0 To (UBound(LwpLine1.Coordinates) - 1) / 2
                pointListY(Index) = LwpLine1.Coordinates(Index * 2 + 1)
            Next
            
            sumX = 0
            For Index = 0 To UBound(pointListX)
                sumX = pointListX(Index) + sumX
            Next
            
            sumY = 0
            For Index = 0 To UBound(pointListY)
                sumY = pointListY(Index) + sumY
            Next
            textPoint(0) = Round(sumX / (UBound(pointListX) + 1), 2)
            textPoint(1) = Round(sumY / (UBound(pointListY) + 1), 2)
            textPoint(2) = 0
            
            Set objCircle = ThisDrawing.ModelSpace.AddCircle(textPoint, 25)
            objCircle.Layer = "AREATEXT"
            objCircle.Update
            
            Set objText = ThisDrawing.ModelSpace.AddText(counter, textPoint, 20)
            objText.StyleName = "C40"
            objText.Layer = "AREATEXT"
            objText.Alignment = acAlignmentMiddle
            objText.TextAlignmentPoint = textPoint
            objText.Update
            
            textPoint(1) = textPoint(1) - 80
            Set objText = ThisDrawing.ModelSpace.AddText(lwArea, textPoint, 40)
            objText.StyleName = "C40"
            objText.Layer = "AREATEXT"
            objText.Alignment = acAlignmentBottomCenter
            objText.TextAlignmentPoint = textPoint
            objText.Update
            '----------
            
            areaArray(arraySize - 1) = counter
            areaArray(arraySize) = lwArea
            counter = counter + 1
        End If
    Loop
Z:
varP0 = ThisDrawing.Utility.GetPoint(, "請選擇表單插入位置")

tablePoint(0) = varP0(0): tablePoint(1) = varP0(1)
tablePoint(2) = tablePoint(0) + 100: tablePoint(3) = tablePoint(1)
tablePoint(4) = tablePoint(2): tablePoint(5) = tablePoint(3) - 70
tablePoint(6) = tablePoint(0): tablePoint(7) = tablePoint(5)

Set LwpLine2 = ThisDrawing.ModelSpace.AddLightWeightPolyline(tablePoint)
LwpLine2.Closed = True
LwpLine2.Layer = "AREATEXT"
LwpLine2.Update

'----------表單文字----------
textPoint(0) = tablePoint(0) / 2 + tablePoint(2) / 2
textPoint(1) = tablePoint(1) / 2 + tablePoint(7) / 2
textPoint(2) = 0

Set objText = ThisDrawing.ModelSpace.AddText("NO.", textPoint, 25)
objText.StyleName = "C40"
objText.Layer = "AREATEXT"
objText.Alignment = acAlignmentMiddle
objText.TextAlignmentPoint = textPoint
objText.Update
'----------

tablePoint(0) = tablePoint(2): tablePoint(1) = tablePoint(3)
tablePoint(2) = tablePoint(0) + 200: tablePoint(3) = tablePoint(1)
tablePoint(4) = tablePoint(2): tablePoint(5) = tablePoint(3) - 70
tablePoint(6) = tablePoint(0): tablePoint(7) = tablePoint(5)

Set LwpLine2 = ThisDrawing.ModelSpace.AddLightWeightPolyline(tablePoint)
LwpLine2.Closed = True
LwpLine2.Layer = "AREATEXT"
LwpLine2.Update

'----------表單文字----------
textPoint(0) = tablePoint(0) / 2 + tablePoint(2) / 2
textPoint(1) = tablePoint(1) / 2 + tablePoint(7) / 2
textPoint(2) = 0

Set objText = ThisDrawing.ModelSpace.AddText("AREA(M2)", textPoint, 25)
objText.StyleName = "C40"
objText.Layer = "AREATEXT"
objText.Alignment = acAlignmentMiddle
objText.TextAlignmentPoint = textPoint
objText.Update
'----------

tablePoint(0) = varP0(0): tablePoint(1) = varP0(1) - 70
For Index = 0 To UBound(areaArray) Step 2
    tablePoint(0) = tablePoint(0): tablePoint(1) = tablePoint(1)
    tablePoint(2) = tablePoint(0) + 100: tablePoint(3) = tablePoint(1)
    tablePoint(4) = tablePoint(2): tablePoint(5) = tablePoint(3) - 70
    tablePoint(6) = tablePoint(0): tablePoint(7) = tablePoint(5)

    Set LwpLine2 = ThisDrawing.ModelSpace.AddLightWeightPolyline(tablePoint)
    LwpLine2.Closed = True
    LwpLine2.Layer = "AREATEXT"
    LwpLine2.Update
    
    '----------表單文字----------
    textPoint(0) = tablePoint(0) / 2 + tablePoint(2) / 2
    textPoint(1) = tablePoint(1) / 2 + tablePoint(7) / 2
    textPoint(2) = 0
    
    Set objCircle = ThisDrawing.ModelSpace.AddCircle(textPoint, 25)
    objCircle.Layer = "AREATEXT"
    objCircle.Update

    Set objText = ThisDrawing.ModelSpace.AddText(areaArray(Index), textPoint, 20)
    objText.StyleName = "C40"
    objText.Layer = "AREATEXT"
    objText.Alignment = acAlignmentMiddle
    objText.TextAlignmentPoint = textPoint
    objText.Update
    '----------

    tablePoint(0) = tablePoint(2): tablePoint(1) = tablePoint(3)
    tablePoint(2) = tablePoint(0) + 200: tablePoint(3) = tablePoint(1)
    tablePoint(4) = tablePoint(2): tablePoint(5) = tablePoint(3) - 70
    tablePoint(6) = tablePoint(0): tablePoint(7) = tablePoint(5)

    Set LwpLine2 = ThisDrawing.ModelSpace.AddLightWeightPolyline(tablePoint)
    LwpLine2.Closed = True
    LwpLine2.Layer = "AREATEXT"
    LwpLine2.Update
    
    '----------表單文字----------
    textPoint(0) = tablePoint(0) / 2 + tablePoint(2) / 2
    textPoint(1) = tablePoint(1) / 2 + tablePoint(7) / 2
    textPoint(2) = 0

    Set objText = ThisDrawing.ModelSpace.AddText(areaArray(Index + 1), textPoint, 40)
    objText.StyleName = "C40"
    objText.Layer = "AREATEXT"
    objText.Alignment = acAlignmentMiddle
    objText.TextAlignmentPoint = textPoint
    objText.Update
    '----------
    
    tablePoint(0) = tablePoint(6) - 100: tablePoint(1) = tablePoint(7)
Next

tablePoint(0) = tablePoint(0): tablePoint(1) = tablePoint(1)
tablePoint(2) = tablePoint(0) + 100: tablePoint(3) = tablePoint(1)
tablePoint(4) = tablePoint(2): tablePoint(5) = tablePoint(3) - 70
tablePoint(6) = tablePoint(0): tablePoint(7) = tablePoint(5)

Set LwpLine2 = ThisDrawing.ModelSpace.AddLightWeightPolyline(tablePoint)
LwpLine2.Closed = True
LwpLine2.Layer = "AREATEXT"
LwpLine2.Update

'----------表單文字----------
textPoint(0) = tablePoint(0) / 2 + tablePoint(2) / 2
textPoint(1) = tablePoint(1) / 2 + tablePoint(7) / 2
textPoint(2) = 0

Set objText = ThisDrawing.ModelSpace.AddText("TOTAL", textPoint, 25)
objText.StyleName = "C40"
objText.Layer = "AREATEXT"
objText.Alignment = acAlignmentMiddle
objText.TextAlignmentPoint = textPoint
objText.Update
'----------

tablePoint(0) = tablePoint(2): tablePoint(1) = tablePoint(3)
tablePoint(2) = tablePoint(0) + 200: tablePoint(3) = tablePoint(1)
tablePoint(4) = tablePoint(2): tablePoint(5) = tablePoint(3) - 70
tablePoint(6) = tablePoint(0): tablePoint(7) = tablePoint(5)

Set LwpLine2 = ThisDrawing.ModelSpace.AddLightWeightPolyline(tablePoint)
LwpLine2.Closed = True
LwpLine2.Layer = "AREATEXT"
LwpLine2.Update

For Index = 0 To UBound(areaArray) Step 2
    total = total + areaArray(Index + 1)
Next

'----------表單文字----------
textPoint(0) = tablePoint(0) / 2 + tablePoint(2) / 2
textPoint(1) = tablePoint(1) / 2 + tablePoint(7) / 2
textPoint(2) = 0

Set objText = ThisDrawing.ModelSpace.AddText(total, textPoint, 40)
objText.StyleName = "C40"
objText.Layer = "AREATEXT"
objText.Alignment = acAlignmentMiddle
objText.TextAlignmentPoint = textPoint
objText.Update
'----------
End Sub

Attribute VB_Name = "layerFunction"
Public Sub CreateLayer(LayerName As String, Color As Integer, LineTypeName As String, Optional Overlay As Boolean = False)
    Dim objAcadLayer As AcadLayer
    Dim objLineType As AcadLineType
    Dim strCurrentLayer As String
    
    strCurrentLayer = ThisDrawing.ActiveLayer.Name
    On Error GoTo ErrorHandle
    If IsExistLayer(LayerName) Then
        Set objAcadLayer = ThisDrawing.Layers.Item(LayerName)
    Else
        Set objAcadLayer = ThisDrawing.Layers.Add(LayerName)
    End If
    objAcadLayer.Color = Color
    If Not IsExistLineType(LineTypeName) Then
        ThisDrawing.Linetypes.Load LineTypeName, "acad.lin"
    End If
    objAcadLayer.LineType = LineTypeName
    
Exit Sub

ErrorHandle:
    MsgBox Err.Description + " LayerName=" + LayerName + ",LineTypeName=" + LineTypeName
    
End Sub

Public Function IsExistLayer(LayerName As String) As Boolean
    On Error Resume Next
    Dim objLayer As AcadLayer
    
    Set objLayer = ThisDrawing.Layers.Item(LayerName)
    If Err.Number <> 0 Then
        IsExistLayer = False
    Else
        IsExistLayer = True
    End If
    
End Function

Public Function IsExistLineType(LineType As String) As Boolean
    Dim objLineType As AcadLineType
    
    On Error Resume Next
    Set objLineType = ThisDrawing.Linetypes.Item(LineType)
    If Err.Number <> 0 Then
        IsExistLineType = False
    Else
        IsExistLineType = True
    End If
End Function
