Attribute VB_Name = "LayerFunction"
Sub LockAll()
Dim objAcadLayer As AcadLayer
Dim strLayerName As String
For Each objAcadLayer In ThisDrawing.Layers
    objAcadLayer.Lock = True
Next
MsgBox ("All layers are locked!!")
End Sub

Sub UnLockAll()
Dim objAcadLayer As AcadLayer
Dim strLayerName As String
For Each objAcadLayer In ThisDrawing.Layers
    objAcadLayer.Lock = False
Next
MsgBox ("All layers are unlocked!!")
End Sub

Sub FreezeAll()
Dim objAcadLayer As AcadLayer
Dim strLayerName As String
On Error Resume Next
For Each objAcadLayer In ThisDrawing.Layers
    objAcadLayer.Freeze = True
Next
MsgBox ("All layers are freezed!!")
End Sub

Sub UnFreezeAll()
Dim objAcadLayer As AcadLayer
Dim strLayerName As String
On Error Resume Next
For Each objAcadLayer In ThisDrawing.Layers
    objAcadLayer.Freeze = False
Next
MsgBox ("All layers are unfreezed!!")
End Sub

Sub LockChoose()
Dim objAcadLayer As AcadLayer
Dim strLayerName As String
Dim objAcadEntity As AcadEntity
Dim objAcadSelectionSet As AcadSelectionSet

On Error Resume Next
ThisDrawing.SelectionSets.Item("ChooseToLock").Delete
Err.Clear

Set objAcadSelectionSet = ThisDrawing.SelectionSets.Add("ChooseToLock")

AcadDoc.Utility.Prompt ("請於圖面上框選欲鎖住之圖層")
objAcadSelectionSet.SelectOnScreen

For Each objAcadEntity In objAcadSelectionSet
    For Each objAcadLayer In ThisDrawing.Layers
        If objAcadLayer.Name = objAcadEntity.Layer Then
            objAcadLayer.Lock = True
        End If
    Next
Next
MsgBox ("Layers are locked")
End Sub

Sub UnLockChoose()
Dim objAcadLayer As AcadLayer
Dim strLayerName As String
Dim objAcadEntity As AcadEntity
Dim objAcadSelectionSet As AcadSelectionSet

On Error Resume Next
ThisDrawing.SelectionSets.Item("ChooseToUnLock").Delete
Err.Clear

Set objAcadSelectionSet = ThisDrawing.SelectionSets.Add("ChooseToUnLock")

AcadDoc.Utility.Prompt ("請於圖面上框選欲解鎖之圖層")
objAcadSelectionSet.SelectOnScreen

For Each objAcadEntity In objAcadSelectionSet
    For Each objAcadLayer In ThisDrawing.Layers
        If objAcadLayer.Name = objAcadEntity.Layer Then
            objAcadLayer.Lock = False
        End If
    Next
Next
MsgBox ("Layers are unlocked")
End Sub
