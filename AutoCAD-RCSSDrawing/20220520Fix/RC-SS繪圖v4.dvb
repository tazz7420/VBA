Attribute VB_Name = "BasicForm"
Attribute VB_Base = "0{F014F966-E001-47AC-BD86-3671E17600A3}{AE459BAF-1557-47CF-9531-7C37F6AD73C0}"
Attribute VB_GlobalNameSpace = False
Attribute VB_Creatable = False
Attribute VB_PredeclaredId = True
Attribute VB_Exposed = False
Attribute VB_TemplateDerived = False
Attribute VB_Customizable = False
Private Sub CmdRCBasic_Click()
    Me.Hide
    RCBasic.show
End Sub

Private Sub CmdRCBeams_Click()
    Me.Hide
    RCBeams.show
End Sub

Private Sub CmdRCBeamsJr_Click()
    Me.Hide
    RCBeamsJr.show
End Sub

Private Sub CmdRCPanel_Click()
    Me.Hide
    RCPanel.show
End Sub

Private Sub CmdRCPillar_Click()
    Me.Hide
    RCPillar.show
End Sub

Private Sub CmdSSBeams_Click()
    Me.Hide
    SSBeams.show
End Sub

Private Sub CmdSSBeamsJr_Click()
    Me.Hide
    SSBeamsJr.show
End Sub

Private Sub CmdSSPanel_Click()
    Me.Hide
    SSPanel.show
End Sub

Private Sub CmdSSPillar_Click()
    Me.Hide
    SSPillar.show
End Sub


Private Sub CommandButton10_Click()

End Sub

Attribute VB_Name = "DrawingFunction"
Public Function PI() As Double
    Dim dblReturn As Double
    dblReturn = Atn(1) * 4
    PI = dblReturn
End Function
Public Function DrawRectangle(varP0 As Variant, varP1 As Variant) As AcadLWPolyline
        
    Dim adblCoordinate(0 To 7) As Double
    adblCoordinate(0) = varP0(0): adblCoordinate(1) = varP0(1)
    adblCoordinate(2) = varP1(0):      adblCoordinate(3) = varP0(1)
    adblCoordinate(4) = varP1(0):      adblCoordinate(5) = varP1(1)
    adblCoordinate(6) = varP0(0):      adblCoordinate(7) = varP1(1)
   
    Dim objAddLightWeightPolyline As AcadLWPolyline
    Set objAddLightWeightPolyline = ThisDrawing.ModelSpace.AddLightWeightPolyline(adblCoordinate)
    
    objAddLightWeightPolyline.Closed = True

    Set DrawRectangle = objAddLightWeightPolyline
    
End Function

Public Function GetDistance(varP1 As Variant, varP2 As Variant) As Double
    Dim dblReturn As Double
    
    dblReturn = ((varP2(0) - varP1(0)) ^ 2 + _
                (varP2(1) - varP1(1)) ^ 2 + _
                (varP2(2) - varP1(2)) ^ 2) ^ 0.5
                
    GetDistance = dblReturn
End Function

Attribute VB_Name = "LayerFunction"
Public Sub CreateLayer(LayerName As String, Color As Integer, LineTypeName As String, Optional Overlay As Boolean = False)
    Dim objAcadLayer As AcadLayer
    Dim objLineType As AcadLineType
    Dim strCurrentLayer As String
    
    strCurrentLayer = ThisDrawing.ActiveLayer.Name
    On Error GoTo ErrorHandle
    If IsExistLayer(LayerName) Then
        Set objAcadLayer = ThisDrawing.Layers.Item(LayerName)
    Else
        Set objAcadLayer = ThisDrawing.Layers.Add(LayerName)
    End If
    objAcadLayer.Color = Color
    If Not IsExistLineType(LineTypeName) Then
        ThisDrawing.Linetypes.Load LineTypeName, "acad.lin"
    End If
    objAcadLayer.LineType = LineTypeName
    
Exit Sub

ErrorHandle:
    MsgBox Err.Description + " LayerName=" + LayerName + ",LineTypeName=" + LineTypeName
    
End Sub

Public Function IsExistLayer(LayerName As String) As Boolean
    On Error Resume Next
    Dim objLayer As AcadLayer
    
    Set objLayer = ThisDrawing.Layers.Item(LayerName)
    If Err.Number <> 0 Then
        IsExistLayer = False
    Else
        IsExistLayer = True
    End If
    
End Function

Public Function IsExistLineType(LineType As String) As Boolean
    Dim objLineType As AcadLineType
    
    On Error Resume Next
    Set objLineType = ThisDrawing.Linetypes.Item(LineType)
    If Err.Number <> 0 Then
        IsExistLineType = False
    Else
        IsExistLineType = True
    End If
End Function

Attribute VB_Name = "RCBasic"
Attribute VB_Base = "0{BBD179A4-E8A6-4042-B98C-B190AA31C03F}{875F5337-0659-47CF-A717-A044D88A7F84}"
Attribute VB_GlobalNameSpace = False
Attribute VB_Creatable = False
Attribute VB_PredeclaredId = True
Attribute VB_Exposed = False
Attribute VB_TemplateDerived = False
Attribute VB_Customizable = False
Private Sub cmdCancel_Click()
    Me.Hide
    BasicForm.show
End Sub

Private Sub chkDown_Click()
    If Me.chkDown.Value = True Then
        Me.chkUp.Value = False
        Me.chkMiddle.Value = False
    End If
End Sub

Private Sub chkMiddle_Click()
    If Me.chkMiddle.Value = True Then
        Me.chkUp.Value = False
        Me.chkDown.Value = False
    End If
End Sub

Private Sub chkUp_Click()
    If Me.chkUp.Value = True Then
        Me.chkMiddle.Value = False
        Me.chkDown.Value = False
    End If
End Sub

Private Sub cmdDraw_Click()
    Dim strN, strNN As String
    Dim dblW, Dist1, Ang1 As Double
    Dim intNum As Integer
    Dim varP0, varP1 As Variant
    Dim P1, P2, P3, P4, P5, P6, P7, P8, P9, P10, P11, P12, P13, P14, P15, P16 As Variant
    Dim Coordinates(0 To 7) As Double
    Dim Coordinatess(0 To 9) As Double
    Dim objLwline As AcadLWPolyline
    Dim objText1 As AcadText
    
    Me.Hide
    Call CreateLayer("FOOT", 1, "HIDDEN")
    Call CreateLayer("FOOTT", 6, "CONTINUOUS")
    Call CreateLayer("DIM", 3, "CONTINUOUS")
    dblW = Val(Me.txtW.Value)
    strN = Me.txtN.Value
    strNN = Me.txtNN.Value
    intNum = Me.txtNum
    On Error GoTo Z
    If Me.chkContinue.Value = True Then
    Do While Err.Number = 0
        If Me.chkUp.Value = True Then
            With ThisDrawing.Utility
                varP0 = .GetPoint(, "P1")
                varP1 = .GetPoint(varP0, "P2")
                Dist1 = GetDistance(varP0, varP1)
                Ang1 = .AngleFromXAxis(varP0, varP1)
                P1 = .PolarPoint(varP0, Ang1, -40)
                P2 = .PolarPoint(varP1, Ang1, 40)
                P3 = .PolarPoint(P1, Ang1 + PI / 2, dblW)
                P4 = .PolarPoint(P2, Ang1 + PI / 2, dblW)
                P5 = .PolarPoint(P1, Ang1 + PI / 2, dblW / 2)
                P6 = .PolarPoint(P5, Ang1 + PI, 70)
                P7 = .PolarPoint(P5, Ang1 + PI - PI / 12, 10)
                P8 = .PolarPoint(P5, Ang1 + PI + PI / 12, 10)
                P9 = .PolarPoint(P6, Ang1 + PI / 2, 25)
                P10 = .PolarPoint(P6, Ang1 - PI / 2, 25)
                P11 = .PolarPoint(P9, Ang1, -120)
                P12 = .PolarPoint(P10, Ang1, -120)
                P13 = .PolarPoint(P6, Ang1, -60)
            End With
            Coordinates(0) = P1(0): Coordinates(1) = P1(1)
            Coordinates(2) = P2(0): Coordinates(3) = P2(1)
            Coordinates(4) = P4(0): Coordinates(5) = P4(1)
            Coordinates(6) = P3(0): Coordinates(7) = P3(1)
            Set objLwline = ThisDrawing.ModelSpace.AddLightWeightPolyline(Coordinates)
            objLwline.Closed = True
            objLwline.Layer = "FOOT"
            objLwline.Update
            Coordinates(0) = P9(0): Coordinates(1) = P9(1)
            Coordinates(2) = P10(0): Coordinates(3) = P10(1)
            Coordinates(4) = P12(0): Coordinates(5) = P12(1)
            Coordinates(6) = P11(0): Coordinates(7) = P11(1)
            Set objLwline = ThisDrawing.ModelSpace.AddLightWeightPolyline(Coordinates)
            objLwline.Closed = True
            objLwline.Layer = "DIM"
            objLwline.Update
            Coordinatess(0) = P5(0): Coordinatess(1) = P5(1)
            Coordinatess(2) = P7(0): Coordinatess(3) = P7(1)
            Coordinatess(4) = P8(0): Coordinatess(5) = P8(1)
            Coordinatess(6) = P5(0): Coordinatess(7) = P5(1)
            Coordinatess(8) = P6(0): Coordinatess(9) = P6(1)
            Set objLwline = ThisDrawing.ModelSpace.AddLightWeightPolyline(Coordinatess)
            objLwline.Layer = "DIM"
            Set objText1 = ThisDrawing.ModelSpace.AddText(strN + CStr(intNum) + strNN, P13, 40)
            objText1.StyleName = "C40"
            objText1.Layer = "FOOTT"
            objText1.ScaleFactor = 0.7
            objText1.Alignment = acAlignmentMiddleCenter
            objText1.TextAlignmentPoint = P13
            objText1.Rotate P13, Ang1
            objText1.Update
            intNum = intNum + 1
            Me.txtNum = intNum
        ElseIf Me.chkMiddle.Value = True Then
            With ThisDrawing.Utility
                varP0 = .GetPoint(, "P1")
                varP1 = .GetPoint(varP0, "P2")
                Dist1 = GetDistance(varP0, varP1)
                Ang1 = .AngleFromXAxis(varP0, varP1)
                P1 = .PolarPoint(varP0, Ang1, -40)
                P2 = .PolarPoint(varP1, Ang1, 40)
                P3 = .PolarPoint(P1, Ang1 + PI / 2, dblW)
                P4 = .PolarPoint(P2, Ang1 + PI / 2, dblW)
                P5 = .PolarPoint(P1, Ang1 + PI / 2, dblW / 2)
                P6 = .PolarPoint(P5, Ang1 + PI, 70)
                P7 = .PolarPoint(P5, Ang1 + PI - PI / 12, 10)
                P8 = .PolarPoint(P5, Ang1 + PI + PI / 12, 10)
                P9 = .PolarPoint(P6, Ang1 + PI / 2, 25)
                P10 = .PolarPoint(P6, Ang1 - PI / 2, 25)
                P11 = .PolarPoint(P9, Ang1, -120)
                P12 = .PolarPoint(P10, Ang1, -120)
                P13 = .PolarPoint(P6, Ang1, -60)
            End With
            Coordinates(0) = P1(0): Coordinates(1) = P1(1)
            Coordinates(2) = P2(0): Coordinates(3) = P2(1)
            Coordinates(4) = P4(0): Coordinates(5) = P4(1)
            Coordinates(6) = P3(0): Coordinates(7) = P3(1)
            Set objLwline = ThisDrawing.ModelSpace.AddLightWeightPolyline(Coordinates)
            objLwline.Closed = True
            objLwline.Move P5, P1
            objLwline.Layer = "FOOT"
            objLwline.Update
            Coordinates(0) = P9(0): Coordinates(1) = P9(1)
            Coordinates(2) = P10(0): Coordinates(3) = P10(1)
            Coordinates(4) = P12(0): Coordinates(5) = P12(1)
            Coordinates(6) = P11(0): Coordinates(7) = P11(1)
            Set objLwline = ThisDrawing.ModelSpace.AddLightWeightPolyline(Coordinates)
            objLwline.Closed = True
            objLwline.Move P5, P1
            objLwline.Layer = "DIM"
            objLwline.Update
            Coordinatess(0) = P5(0): Coordinatess(1) = P5(1)
            Coordinatess(2) = P7(0): Coordinatess(3) = P7(1)
            Coordinatess(4) = P8(0): Coordinatess(5) = P8(1)
            Coordinatess(6) = P5(0): Coordinatess(7) = P5(1)
            Coordinatess(8) = P6(0): Coordinatess(9) = P6(1)
            Set objLwline = ThisDrawing.ModelSpace.AddLightWeightPolyline(Coordinatess)
            objLwline.Layer = "DIM"
            objLwline.Move P5, P1
            Set objText1 = ThisDrawing.ModelSpace.AddText(strN + CStr(intNum) + strNN, P13, 40)
            objText1.StyleName = "C40"
            objText1.Layer = "FOOTT"
            objText1.ScaleFactor = 0.7
            objText1.Alignment = acAlignmentMiddleCenter
            objText1.TextAlignmentPoint = P13
            objText1.Rotate P13, Ang1
            objText1.Move P5, P1
            objText1.Update
            intNum = intNum + 1
            Me.txtNum = intNum
        ElseIf Me.chkDown.Value = True Then
            With ThisDrawing.Utility
                varP0 = .GetPoint(, "P1")
                varP1 = .GetPoint(varP0, "P2")
                Dist1 = GetDistance(varP0, varP1)
                Ang1 = .AngleFromXAxis(varP0, varP1)
                P1 = .PolarPoint(varP0, Ang1, -40)
                P2 = .PolarPoint(varP1, Ang1, 40)
                P3 = .PolarPoint(P1, Ang1 + PI / 2, dblW)
                P4 = .PolarPoint(P2, Ang1 + PI / 2, dblW)
                P5 = .PolarPoint(P1, Ang1 + PI / 2, dblW / 2)
                P6 = .PolarPoint(P5, Ang1 + PI, 70)
                P7 = .PolarPoint(P5, Ang1 + PI - PI / 12, 10)
                P8 = .PolarPoint(P5, Ang1 + PI + PI / 12, 10)
                P9 = .PolarPoint(P6, Ang1 + PI / 2, 25)
                P10 = .PolarPoint(P6, Ang1 - PI / 2, 25)
                P11 = .PolarPoint(P9, Ang1, -120)
                P12 = .PolarPoint(P10, Ang1, -120)
                P13 = .PolarPoint(P6, Ang1, -60)
            End With
            Coordinates(0) = P1(0): Coordinates(1) = P1(1)
            Coordinates(2) = P2(0): Coordinates(3) = P2(1)
            Coordinates(4) = P4(0): Coordinates(5) = P4(1)
            Coordinates(6) = P3(0): Coordinates(7) = P3(1)
            Set objLwline = ThisDrawing.ModelSpace.AddLightWeightPolyline(Coordinates)
            objLwline.Closed = True
            objLwline.Move P3, P1
            objLwline.Layer = "FOOT"
            objLwline.Update
            Coordinates(0) = P9(0): Coordinates(1) = P9(1)
            Coordinates(2) = P10(0): Coordinates(3) = P10(1)
            Coordinates(4) = P12(0): Coordinates(5) = P12(1)
            Coordinates(6) = P11(0): Coordinates(7) = P11(1)
            Set objLwline = ThisDrawing.ModelSpace.AddLightWeightPolyline(Coordinates)
            objLwline.Closed = True
            objLwline.Move P3, P1
            objLwline.Layer = "DIM"
            objLwline.Update
            Coordinatess(0) = P5(0): Coordinatess(1) = P5(1)
            Coordinatess(2) = P7(0): Coordinatess(3) = P7(1)
            Coordinatess(4) = P8(0): Coordinatess(5) = P8(1)
            Coordinatess(6) = P5(0): Coordinatess(7) = P5(1)
            Coordinatess(8) = P6(0): Coordinatess(9) = P6(1)
            Set objLwline = ThisDrawing.ModelSpace.AddLightWeightPolyline(Coordinatess)
            objLwline.Layer = "DIM"
            objLwline.Move P3, P1
            Set objText1 = ThisDrawing.ModelSpace.AddText(strN + CStr(intNum) + strNN, P13, 40)
            objText1.StyleName = "C40"
            objText1.Layer = "FOOTT"
            objText1.ScaleFactor = 0.7
            objText1.Alignment = acAlignmentMiddleCenter
            objText1.TextAlignmentPoint = P13
            objText1.Rotate P13, Ang1
            objText1.Move P3, P1
            objText1.Update
            intNum = intNum + 1
            Me.txtNum = intNum
        End If
    Loop
    Else
    Do While Err.Number = 0
        If Me.chkUp.Value = True Then
            With ThisDrawing.Utility
                varP0 = .GetPoint(, "P1")
                varP1 = .GetPoint(varP0, "P2")
                Dist1 = GetDistance(varP0, varP1)
                Ang1 = .AngleFromXAxis(varP0, varP1)
                P1 = .PolarPoint(varP0, Ang1, -40)
                P2 = .PolarPoint(varP1, Ang1, 40)
                P3 = .PolarPoint(P1, Ang1 + PI / 2, dblW)
                P4 = .PolarPoint(P2, Ang1 + PI / 2, dblW)
                P5 = .PolarPoint(P1, Ang1 + PI / 2, dblW / 2)
                P6 = .PolarPoint(P5, Ang1 + PI, 70)
                P7 = .PolarPoint(P5, Ang1 + PI - PI / 12, 10)
                P8 = .PolarPoint(P5, Ang1 + PI + PI / 12, 10)
                P9 = .PolarPoint(P6, Ang1 + PI / 2, 25)
                P10 = .PolarPoint(P6, Ang1 - PI / 2, 25)
                P11 = .PolarPoint(P9, Ang1, -120)
                P12 = .PolarPoint(P10, Ang1, -120)
                P13 = .PolarPoint(P6, Ang1, -60)
            End With
            Coordinates(0) = P1(0): Coordinates(1) = P1(1)
            Coordinates(2) = P2(0): Coordinates(3) = P2(1)
            Coordinates(4) = P4(0): Coordinates(5) = P4(1)
            Coordinates(6) = P3(0): Coordinates(7) = P3(1)
            Set objLwline = ThisDrawing.ModelSpace.AddLightWeightPolyline(Coordinates)
            objLwline.Closed = True
            objLwline.Layer = "FOOT"
            objLwline.Update
            Coordinates(0) = P9(0): Coordinates(1) = P9(1)
            Coordinates(2) = P10(0): Coordinates(3) = P10(1)
            Coordinates(4) = P12(0): Coordinates(5) = P12(1)
            Coordinates(6) = P11(0): Coordinates(7) = P11(1)
            Set objLwline = ThisDrawing.ModelSpace.AddLightWeightPolyline(Coordinates)
            objLwline.Closed = True
            objLwline.Layer = "DIM"
            objLwline.Update
            Coordinatess(0) = P5(0): Coordinatess(1) = P5(1)
            Coordinatess(2) = P7(0): Coordinatess(3) = P7(1)
            Coordinatess(4) = P8(0): Coordinatess(5) = P8(1)
            Coordinatess(6) = P5(0): Coordinatess(7) = P5(1)
            Coordinatess(8) = P6(0): Coordinatess(9) = P6(1)
            Set objLwline = ThisDrawing.ModelSpace.AddLightWeightPolyline(Coordinatess)
            objLwline.Layer = "DIM"
            Set objText1 = ThisDrawing.ModelSpace.AddText(strN + CStr(intNum) + strNN, P13, 40)
            objText1.StyleName = "C40"
            objText1.Layer = "FOOTT"
            objText1.ScaleFactor = 0.7
            objText1.Alignment = acAlignmentMiddleCenter
            objText1.TextAlignmentPoint = P13
            objText1.Rotate P13, Ang1
            objText1.Update
        ElseIf Me.chkMiddle.Value = True Then
            With ThisDrawing.Utility
                varP0 = .GetPoint(, "P1")
                varP1 = .GetPoint(varP0, "P2")
                Dist1 = GetDistance(varP0, varP1)
                Ang1 = .AngleFromXAxis(varP0, varP1)
                P1 = .PolarPoint(varP0, Ang1, -40)
                P2 = .PolarPoint(varP1, Ang1, 40)
                P3 = .PolarPoint(P1, Ang1 + PI / 2, dblW)
                P4 = .PolarPoint(P2, Ang1 + PI / 2, dblW)
                P5 = .PolarPoint(P1, Ang1 + PI / 2, dblW / 2)
                P6 = .PolarPoint(P5, Ang1 + PI, 70)
                P7 = .PolarPoint(P5, Ang1 + PI - PI / 12, 10)
                P8 = .PolarPoint(P5, Ang1 + PI + PI / 12, 10)
                P9 = .PolarPoint(P6, Ang1 + PI / 2, 25)
                P10 = .PolarPoint(P6, Ang1 - PI / 2, 25)
                P11 = .PolarPoint(P9, Ang1, -120)
                P12 = .PolarPoint(P10, Ang1, -120)
                P13 = .PolarPoint(P6, Ang1, -60)
            End With
            Coordinates(0) = P1(0): Coordinates(1) = P1(1)
            Coordinates(2) = P2(0): Coordinates(3) = P2(1)
            Coordinates(4) = P4(0): Coordinates(5) = P4(1)
            Coordinates(6) = P3(0): Coordinates(7) = P3(1)
            Set objLwline = ThisDrawing.ModelSpace.AddLightWeightPolyline(Coordinates)
            objLwline.Closed = True
            objLwline.Move P5, P1
            objLwline.Layer = "FOOT"
            objLwline.Update
            Coordinates(0) = P9(0): Coordinates(1) = P9(1)
            Coordinates(2) = P10(0): Coordinates(3) = P10(1)
            Coordinates(4) = P12(0): Coordinates(5) = P12(1)
            Coordinates(6) = P11(0): Coordinates(7) = P11(1)
            Set objLwline = ThisDrawing.ModelSpace.AddLightWeightPolyline(Coordinates)
            objLwline.Closed = True
            objLwline.Move P5, P1
            objLwline.Layer = "DIM"
            objLwline.Update
            Coordinatess(0) = P5(0): Coordinatess(1) = P5(1)
            Coordinatess(2) = P7(0): Coordinatess(3) = P7(1)
            Coordinatess(4) = P8(0): Coordinatess(5) = P8(1)
            Coordinatess(6) = P5(0): Coordinatess(7) = P5(1)
            Coordinatess(8) = P6(0): Coordinatess(9) = P6(1)
            Set objLwline = ThisDrawing.ModelSpace.AddLightWeightPolyline(Coordinatess)
            objLwline.Layer = "DIM"
            objLwline.Move P5, P1
            Set objText1 = ThisDrawing.ModelSpace.AddText(strN + CStr(intNum) + strNN, P13, 40)
            objText1.StyleName = "C40"
            objText1.Layer = "FOOTT"
            objText1.ScaleFactor = 0.7
            objText1.Alignment = acAlignmentMiddleCenter
            objText1.TextAlignmentPoint = P13
            objText1.Rotate P13, Ang1
            objText1.Move P5, P1
            objText1.Update
        ElseIf Me.chkDown.Value = True Then
            With ThisDrawing.Utility
                varP0 = .GetPoint(, "P1")
                varP1 = .GetPoint(varP0, "P2")
                Dist1 = GetDistance(varP0, varP1)
                Ang1 = .AngleFromXAxis(varP0, varP1)
                P1 = .PolarPoint(varP0, Ang1, -40)
                P2 = .PolarPoint(varP1, Ang1, 40)
                P3 = .PolarPoint(P1, Ang1 + PI / 2, dblW)
                P4 = .PolarPoint(P2, Ang1 + PI / 2, dblW)
                P5 = .PolarPoint(P1, Ang1 + PI / 2, dblW / 2)
                P6 = .PolarPoint(P5, Ang1 + PI, 70)
                P7 = .PolarPoint(P5, Ang1 + PI - PI / 12, 10)
                P8 = .PolarPoint(P5, Ang1 + PI + PI / 12, 10)
                P9 = .PolarPoint(P6, Ang1 + PI / 2, 25)
                P10 = .PolarPoint(P6, Ang1 - PI / 2, 25)
                P11 = .PolarPoint(P9, Ang1, -120)
                P12 = .PolarPoint(P10, Ang1, -120)
                P13 = .PolarPoint(P6, Ang1, -60)
            End With
            Coordinates(0) = P1(0): Coordinates(1) = P1(1)
            Coordinates(2) = P2(0): Coordinates(3) = P2(1)
            Coordinates(4) = P4(0): Coordinates(5) = P4(1)
            Coordinates(6) = P3(0): Coordinates(7) = P3(1)
            Set objLwline = ThisDrawing.ModelSpace.AddLightWeightPolyline(Coordinates)
            objLwline.Closed = True
            objLwline.Move P3, P1
            objLwline.Layer = "FOOT"
            objLwline.Update
            Coordinates(0) = P9(0): Coordinates(1) = P9(1)
            Coordinates(2) = P10(0): Coordinates(3) = P10(1)
            Coordinates(4) = P12(0): Coordinates(5) = P12(1)
            Coordinates(6) = P11(0): Coordinates(7) = P11(1)
            Set objLwline = ThisDrawing.ModelSpace.AddLightWeightPolyline(Coordinates)
            objLwline.Closed = True
            objLwline.Move P3, P1
            objLwline.Layer = "DIM"
            objLwline.Update
            Coordinatess(0) = P5(0): Coordinatess(1) = P5(1)
            Coordinatess(2) = P7(0): Coordinatess(3) = P7(1)
            Coordinatess(4) = P8(0): Coordinatess(5) = P8(1)
            Coordinatess(6) = P5(0): Coordinatess(7) = P5(1)
            Coordinatess(8) = P6(0): Coordinatess(9) = P6(1)
            Set objLwline = ThisDrawing.ModelSpace.AddLightWeightPolyline(Coordinatess)
            objLwline.Layer = "DIM"
            objLwline.Move P3, P1
            Set objText1 = ThisDrawing.ModelSpace.AddText(strN + CStr(intNum) + strNN, P13, 40)
            objText1.StyleName = "C40"
            objText1.Layer = "FOOTT"
            objText1.ScaleFactor = 0.7
            objText1.Alignment = acAlignmentMiddleCenter
            objText1.TextAlignmentPoint = P13
            objText1.Rotate P13, Ang1
            objText1.Move P3, P1
            objText1.Update
        End If
    Loop
    End If
Z:
    Me.show
End Sub

Private Sub Label1_Click()

End Sub

Attribute VB_Name = "RCBeams"
Attribute VB_Base = "0{A3ACCF7E-AC35-4AE1-BA31-1C6438CFC784}{844E7455-D3B7-4187-800C-38E674E7E385}"
Attribute VB_GlobalNameSpace = False
Attribute VB_Creatable = False
Attribute VB_PredeclaredId = True
Attribute VB_Exposed = False
Attribute VB_TemplateDerived = False
Attribute VB_Customizable = False

Private Sub chkDown_Click()
    If Me.chkDown.Value = True Then
        Me.chkUp.Value = False
        Me.chkMiddle.Value = False
    End If
End Sub

Private Sub chkMiddle_Click()
    If Me.chkMiddle.Value = True Then
        Me.chkUp.Value = False
        Me.chkDown.Value = False
    End If
End Sub

Private Sub chkUp_Click()
    If Me.chkUp.Value = True Then
        Me.chkMiddle.Value = False
        Me.chkDown.Value = False
    End If
End Sub

Private Sub cmdCancel_Click()
    Me.Hide
    BasicForm.show
End Sub


Private Sub cmdDraw_Click()
    Dim varP0, varP1, varP2, varP22, varP3, varP33, varP4, varP5 As Variant
    Dim intNum As Integer
    Dim strN As String
    Dim dblW, Dist1, Ang1 As Double
    Dim adblCoordinate(0 To 7) As Double
    Dim objAddLightWeightPolyline As AcadLWPolyline
    Dim objText1 As AcadText
    
    Me.Hide
    Call CreateLayer("BEAMA", 6, "HIDDEN")
    Call CreateLayer("BEAMT", 3, "CONTINUOUS")
    intNum = Me.txtNum
    strN = Me.txtN
    dblW = Val(Me.txtW)
    If Me.chkContinue.Value = True Then
        If chkUp.Value = True Then
            Do While Err.Number = 0
                On Error GoTo Z
                varP0 = ThisDrawing.Utility.GetPoint(, "點1")
                varP1 = ThisDrawing.Utility.GetPoint(varP0, "點2")
                Ang1 = ThisDrawing.Utility.AngleFromXAxis(varP0, varP1)
                varP2 = ThisDrawing.Utility.PolarPoint(varP1, PI / 2 + Ang1, dblW)
                varP3 = ThisDrawing.Utility.PolarPoint(varP0, PI / 2 + Ang1, dblW)
                Dist1 = GetDistance(varP0, varP1)
                varP4 = ThisDrawing.Utility.PolarPoint(varP3, Ang1, Dist1 / 2)
                varP4 = ThisDrawing.Utility.PolarPoint(varP4, Ang1 + PI / 2, 5)
                adblCoordinate(0) = varP0(0)
                adblCoordinate(1) = varP0(1)
                adblCoordinate(2) = varP1(0)
                adblCoordinate(3) = varP1(1)
                adblCoordinate(4) = varP2(0)
                adblCoordinate(5) = varP2(1)
                adblCoordinate(6) = varP3(0)
                adblCoordinate(7) = varP3(1)
   
                Set objAddLightWeightPolyline = ThisDrawing.ModelSpace.AddLightWeightPolyline(adblCoordinate)
                objAddLightWeightPolyline.Closed = True
                objAddLightWeightPolyline.Layer = "BEAMA"
                objAddLightWeightPolyline.Update
                Set objText1 = ThisDrawing.ModelSpace.AddText(strN + CStr(intNum) + "(" + txtW + ")", varP4, 40)
                objText1.StyleName = "C40"
                objText1.Layer = "BEAMT"
                objText1.ScaleFactor = 0.7
                objText1.Alignment = acAlignmentBottomCenter
                objText1.TextAlignmentPoint = varP4
                objText1.Rotate varP4, Ang1
                objText1.Update
                intNum = intNum + 1
                Me.txtNum = intNum
            Loop
        ElseIf chkMiddle.Value = True Then
            Do While Err.Number = 0
                On Error GoTo Z
                varP0 = ThisDrawing.Utility.GetPoint(, "點1")
                varP1 = ThisDrawing.Utility.GetPoint(varP0, "點2")
                Ang1 = ThisDrawing.Utility.AngleFromXAxis(varP0, varP1)
                varP2 = ThisDrawing.Utility.PolarPoint(varP1, PI / 2 + Ang1, dblW / 2)
                varP3 = ThisDrawing.Utility.PolarPoint(varP0, PI / 2 + Ang1, dblW / 2)
                varP22 = ThisDrawing.Utility.PolarPoint(varP1, PI / -2 + Ang1, dblW / 2)
                varP33 = ThisDrawing.Utility.PolarPoint(varP0, PI / -2 + Ang1, dblW / 2)
                Dist1 = GetDistance(varP0, varP1)
                varP4 = ThisDrawing.Utility.PolarPoint(varP3, Ang1, Dist1 / 2)
                varP4 = ThisDrawing.Utility.PolarPoint(varP4, Ang1 + PI / 2, 5)
                varP5 = ThisDrawing.Utility.PolarPoint(varP4, PI / 2 + Ang1, 2)
                adblCoordinate(0) = varP33(0)
                adblCoordinate(1) = varP33(1)
                adblCoordinate(2) = varP22(0)
                adblCoordinate(3) = varP22(1)
                adblCoordinate(4) = varP2(0)
                adblCoordinate(5) = varP2(1)
                adblCoordinate(6) = varP3(0)
                adblCoordinate(7) = varP3(1)
   
                Set objAddLightWeightPolyline = ThisDrawing.ModelSpace.AddLightWeightPolyline(adblCoordinate)
                objAddLightWeightPolyline.Closed = True
                objAddLightWeightPolyline.Layer = "BEAMA"
                objAddLightWeightPolyline.Update
                Set objText1 = ThisDrawing.ModelSpace.AddText(strN + CStr(intNum) + "(" + txtW + ")", varP4, 40)
                objText1.StyleName = "C40"
                objText1.Layer = "BEAMT"
                objText1.ScaleFactor = 0.7
                objText1.Alignment = acAlignmentBottomCenter
                objText1.TextAlignmentPoint = varP4
                objText1.Rotate varP4, Ang1
                objText1.Update
                intNum = intNum + 1
                Me.txtNum = intNum
            Loop
        ElseIf chkDown.Value = True Then
            Do While Err.Number = 0
                On Error GoTo Z
                varP0 = ThisDrawing.Utility.GetPoint(, "點1")
                varP1 = ThisDrawing.Utility.GetPoint(varP0, "點2")
                Ang1 = ThisDrawing.Utility.AngleFromXAxis(varP0, varP1)
                varP2 = ThisDrawing.Utility.PolarPoint(varP1, PI / -2 + Ang1, dblW)
                varP3 = ThisDrawing.Utility.PolarPoint(varP0, PI / -2 + Ang1, dblW)
                Dist1 = GetDistance(varP0, varP1)
                varP4 = ThisDrawing.Utility.PolarPoint(varP0, Ang1, Dist1 / 2)
                varP4 = ThisDrawing.Utility.PolarPoint(varP4, Ang1 + PI / 2, 5)
                varP5 = ThisDrawing.Utility.PolarPoint(varP4, PI / 2 + Ang1, 2)
                adblCoordinate(0) = varP0(0)
                adblCoordinate(1) = varP0(1)
                adblCoordinate(2) = varP1(0)
                adblCoordinate(3) = varP1(1)
                adblCoordinate(4) = varP2(0)
                adblCoordinate(5) = varP2(1)
                adblCoordinate(6) = varP3(0)
                adblCoordinate(7) = varP3(1)
   
                Set objAddLightWeightPolyline = ThisDrawing.ModelSpace.AddLightWeightPolyline(adblCoordinate)
                objAddLightWeightPolyline.Closed = True
                objAddLightWeightPolyline.Layer = "BEAMA"
                objAddLightWeightPolyline.Update
                Set objText1 = ThisDrawing.ModelSpace.AddText(strN + CStr(intNum) + "(" + txtW + ")", varP4, 40)
                objText1.Layer = "BEAMT"
                objText1.StyleName = "C40"
                objText1.ScaleFactor = 0.7
                objText1.Alignment = acAlignmentBottomCenter
                objText1.TextAlignmentPoint = varP4
                objText1.Rotate varP4, Ang1
                objText1.Update
                intNum = intNum + 1
                Me.txtNum = intNum
            Loop
        End If
    Else
        If chkUp.Value = True Then
            Do While Err.Number = 0
                On Error GoTo Z
                varP0 = ThisDrawing.Utility.GetPoint(, "點1")
                varP1 = ThisDrawing.Utility.GetPoint(varP0, "點2")
                Ang1 = ThisDrawing.Utility.AngleFromXAxis(varP0, varP1)
                varP2 = ThisDrawing.Utility.PolarPoint(varP1, PI / 2 + Ang1, dblW)
                varP3 = ThisDrawing.Utility.PolarPoint(varP0, PI / 2 + Ang1, dblW)
                Dist1 = GetDistance(varP0, varP1)
                varP4 = ThisDrawing.Utility.PolarPoint(varP3, Ang1, Dist1 / 2)
                varP4 = ThisDrawing.Utility.PolarPoint(varP4, Ang1 + PI / 2, 5)
                adblCoordinate(0) = varP0(0)
                adblCoordinate(1) = varP0(1)
                adblCoordinate(2) = varP1(0)
                adblCoordinate(3) = varP1(1)
                adblCoordinate(4) = varP2(0)
                adblCoordinate(5) = varP2(1)
                adblCoordinate(6) = varP3(0)
                adblCoordinate(7) = varP3(1)
   
                Set objAddLightWeightPolyline = ThisDrawing.ModelSpace.AddLightWeightPolyline(adblCoordinate)
                objAddLightWeightPolyline.Closed = True
                objAddLightWeightPolyline.Layer = "BEAMA"
                objAddLightWeightPolyline.Update
                Set objText1 = ThisDrawing.ModelSpace.AddText(strN + CStr(intNum) + "(" + txtW + ")", varP4, 40)
                objText1.Layer = "BEAMT"
                objText1.StyleName = "C40"
                objText1.ScaleFactor = 0.7
                objText1.Alignment = acAlignmentBottomCenter
                objText1.TextAlignmentPoint = varP4
                objText1.Rotate varP4, Ang1
                objText1.Update
            Loop
        ElseIf chkMiddle.Value = True Then
            Do While Err.Number = 0
                On Error GoTo Z
                varP0 = ThisDrawing.Utility.GetPoint(, "點1")
                varP1 = ThisDrawing.Utility.GetPoint(varP0, "點2")
                Ang1 = ThisDrawing.Utility.AngleFromXAxis(varP0, varP1)
                varP2 = ThisDrawing.Utility.PolarPoint(varP1, PI / 2 + Ang1, dblW / 2)
                varP3 = ThisDrawing.Utility.PolarPoint(varP0, PI / 2 + Ang1, dblW / 2)
                varP22 = ThisDrawing.Utility.PolarPoint(varP1, PI / -2 + Ang1, dblW / 2)
                varP33 = ThisDrawing.Utility.PolarPoint(varP0, PI / -2 + Ang1, dblW / 2)
                Dist1 = GetDistance(varP0, varP1)
                varP4 = ThisDrawing.Utility.PolarPoint(varP3, Ang1, Dist1 / 2)
                varP4 = ThisDrawing.Utility.PolarPoint(varP4, Ang1 + PI / 2, 5)
                varP5 = ThisDrawing.Utility.PolarPoint(varP4, PI / 2 + Ang1, 2)
                adblCoordinate(0) = varP33(0)
                adblCoordinate(1) = varP33(1)
                adblCoordinate(2) = varP22(0)
                adblCoordinate(3) = varP22(1)
                adblCoordinate(4) = varP2(0)
                adblCoordinate(5) = varP2(1)
                adblCoordinate(6) = varP3(0)
                adblCoordinate(7) = varP3(1)
   
                Set objAddLightWeightPolyline = ThisDrawing.ModelSpace.AddLightWeightPolyline(adblCoordinate)
                objAddLightWeightPolyline.Closed = True
                objAddLightWeightPolyline.Layer = "BEAMA"
                objAddLightWeightPolyline.Update
                Set objText1 = ThisDrawing.ModelSpace.AddText(strN + CStr(intNum) + "(" + txtW + ")", varP4, 40)
                objText1.Layer = "BEAMT"
                objText1.StyleName = "C40"
                objText1.ScaleFactor = 0.7
                objText1.Alignment = acAlignmentBottomCenter
                objText1.TextAlignmentPoint = varP4
                objText1.Rotate varP4, Ang1
                objText1.Update
            Loop
        ElseIf chkDown.Value = True Then
            Do While Err.Number = 0
                On Error GoTo Z
                varP0 = ThisDrawing.Utility.GetPoint(, "點1")
                varP1 = ThisDrawing.Utility.GetPoint(varP0, "點2")
                Ang1 = ThisDrawing.Utility.AngleFromXAxis(varP0, varP1)
                varP2 = ThisDrawing.Utility.PolarPoint(varP1, PI / -2 + Ang1, dblW)
                varP3 = ThisDrawing.Utility.PolarPoint(varP0, PI / -2 + Ang1, dblW)
                Dist1 = GetDistance(varP0, varP1)
                varP4 = ThisDrawing.Utility.PolarPoint(varP0, Ang1, Dist1 / 2)
                varP4 = ThisDrawing.Utility.PolarPoint(varP4, Ang1 + PI / 2, 5)
                varP5 = ThisDrawing.Utility.PolarPoint(varP4, PI / 2 + Ang1, 2)
                adblCoordinate(0) = varP0(0)
                adblCoordinate(1) = varP0(1)
                adblCoordinate(2) = varP1(0)
                adblCoordinate(3) = varP1(1)
                adblCoordinate(4) = varP2(0)
                adblCoordinate(5) = varP2(1)
                adblCoordinate(6) = varP3(0)
                adblCoordinate(7) = varP3(1)
   
                Set objAddLightWeightPolyline = ThisDrawing.ModelSpace.AddLightWeightPolyline(adblCoordinate)
                objAddLightWeightPolyline.Closed = True
                objAddLightWeightPolyline.Layer = "BEAMA"
                objAddLightWeightPolyline.Update
                Set objText1 = ThisDrawing.ModelSpace.AddText(strN + CStr(intNum) + "(" + txtW + ")", varP4, 40)
                objText1.Layer = "BEAMT"
                objText1.StyleName = "C40"
                objText1.ScaleFactor = 0.7
                objText1.Alignment = acAlignmentBottomCenter
                objText1.TextAlignmentPoint = varP4
                objText1.Rotate varP4, Ang1
                objText1.Update
            Loop
        End If
    End If
Z:
    Me.show
End Sub

Private Sub Label4_Click()

End Sub

Attribute VB_Name = "RCBeamsJr"
Attribute VB_Base = "0{D1AC1E6D-BEC5-42FE-BDD7-CD5E392410E2}{6883E718-0C54-46C7-9092-6CE757C94F32}"
Attribute VB_GlobalNameSpace = False
Attribute VB_Creatable = False
Attribute VB_PredeclaredId = True
Attribute VB_Exposed = False
Attribute VB_TemplateDerived = False
Attribute VB_Customizable = False

Private Sub chkDown_Click()
    If Me.chkDown.Value = True Then
        Me.chkUp.Value = False
        Me.chkMiddle.Value = False
    End If
End Sub

Private Sub chkMiddle_Click()
    If Me.chkMiddle.Value = True Then
        Me.chkUp.Value = False
        Me.chkDown.Value = False
    End If
End Sub

Private Sub chkUp_Click()
    If Me.chkUp.Value = True Then
        Me.chkMiddle.Value = False
        Me.chkDown.Value = False
    End If
End Sub

Private Sub cmdCancel_Click()
    Me.Hide
    BasicForm.show
End Sub


Private Sub cmdDraw_Click()
    Dim varP0, varP1, varP2, varP22, varP3, varP33, varP4, varP5 As Variant
    Dim intNum As Integer
    Dim strN As String
    Dim dblW, Dist1, Ang1 As Double
    Dim adblCoordinate(0 To 7) As Double
    Dim objAddLightWeightPolyline As AcadLWPolyline
    Dim objText1 As AcadText
    
    Me.Hide
    Call CreateLayer("JBEAM", 31, "HIDDEN")
    Call CreateLayer("JBEAMT", 71, "CONTINUOUS")
    intNum = Me.txtNum
    strN = Me.txtN
    dblW = Val(Me.txtW)
    If Me.chkContinue.Value = True Then
        If chkUp.Value = True Then
            Do While Err.Number = 0
                On Error GoTo Z
                varP0 = ThisDrawing.Utility.GetPoint(, "點1")
                varP1 = ThisDrawing.Utility.GetPoint(varP0, "點2")
                Ang1 = ThisDrawing.Utility.AngleFromXAxis(varP0, varP1)
                varP2 = ThisDrawing.Utility.PolarPoint(varP1, PI / 2 + Ang1, dblW)
                varP3 = ThisDrawing.Utility.PolarPoint(varP0, PI / 2 + Ang1, dblW)
                Dist1 = GetDistance(varP0, varP1)
                varP4 = ThisDrawing.Utility.PolarPoint(varP3, Ang1, Dist1 / 2)
                varP4 = ThisDrawing.Utility.PolarPoint(varP4, Ang1 + PI / 2, 5)
                adblCoordinate(0) = varP0(0)
                adblCoordinate(1) = varP0(1)
                adblCoordinate(2) = varP1(0)
                adblCoordinate(3) = varP1(1)
                adblCoordinate(4) = varP2(0)
                adblCoordinate(5) = varP2(1)
                adblCoordinate(6) = varP3(0)
                adblCoordinate(7) = varP3(1)
   
                Set objAddLightWeightPolyline = ThisDrawing.ModelSpace.AddLightWeightPolyline(adblCoordinate)
                objAddLightWeightPolyline.Closed = True
                objAddLightWeightPolyline.Layer = "JBEAM"
                objAddLightWeightPolyline.Update
                Set objText1 = ThisDrawing.ModelSpace.AddText(strN + CStr(intNum) + "(" + txtW + ")", varP4, 40)
                objText1.Layer = "JBEAMT"
                objText1.StyleName = "C40"
                objText1.ScaleFactor = 0.7
                objText1.Alignment = acAlignmentBottomCenter
                objText1.TextAlignmentPoint = varP4
                objText1.Rotate varP4, Ang1
                objText1.Update
                intNum = intNum + 1
                Me.txtNum = intNum
            Loop
        ElseIf chkMiddle.Value = True Then
            Do While Err.Number = 0
                On Error GoTo Z
                varP0 = ThisDrawing.Utility.GetPoint(, "點1")
                varP1 = ThisDrawing.Utility.GetPoint(varP0, "點2")
                Ang1 = ThisDrawing.Utility.AngleFromXAxis(varP0, varP1)
                varP2 = ThisDrawing.Utility.PolarPoint(varP1, PI / 2 + Ang1, dblW / 2)
                varP3 = ThisDrawing.Utility.PolarPoint(varP0, PI / 2 + Ang1, dblW / 2)
                varP22 = ThisDrawing.Utility.PolarPoint(varP1, PI / -2 + Ang1, dblW / 2)
                varP33 = ThisDrawing.Utility.PolarPoint(varP0, PI / -2 + Ang1, dblW / 2)
                Dist1 = GetDistance(varP0, varP1)
                varP4 = ThisDrawing.Utility.PolarPoint(varP3, Ang1, Dist1 / 2)
                varP4 = ThisDrawing.Utility.PolarPoint(varP4, Ang1 + PI / 2, 5)
                varP5 = ThisDrawing.Utility.PolarPoint(varP4, PI / 2 + Ang1, 2)
                adblCoordinate(0) = varP33(0)
                adblCoordinate(1) = varP33(1)
                adblCoordinate(2) = varP22(0)
                adblCoordinate(3) = varP22(1)
                adblCoordinate(4) = varP2(0)
                adblCoordinate(5) = varP2(1)
                adblCoordinate(6) = varP3(0)
                adblCoordinate(7) = varP3(1)
   
                Set objAddLightWeightPolyline = ThisDrawing.ModelSpace.AddLightWeightPolyline(adblCoordinate)
                objAddLightWeightPolyline.Closed = True
                objAddLightWeightPolyline.Layer = "JBEAM"
                objAddLightWeightPolyline.Update
                Set objText1 = ThisDrawing.ModelSpace.AddText(strN + CStr(intNum) + "(" + txtW + ")", varP4, 40)
                objText1.StyleName = "C40"
                objText1.Layer = "JBEAMT"
                objText1.ScaleFactor = 0.7
                objText1.Alignment = acAlignmentBottomCenter
                objText1.TextAlignmentPoint = varP4
                objText1.Rotate varP4, Ang1
                objText1.Update
                intNum = intNum + 1
                Me.txtNum = intNum
            Loop
        ElseIf chkDown.Value = True Then
            Do While Err.Number = 0
                On Error GoTo Z
                varP0 = ThisDrawing.Utility.GetPoint(, "點1")
                varP1 = ThisDrawing.Utility.GetPoint(varP0, "點2")
                Ang1 = ThisDrawing.Utility.AngleFromXAxis(varP0, varP1)
                varP2 = ThisDrawing.Utility.PolarPoint(varP1, PI / -2 + Ang1, dblW)
                varP3 = ThisDrawing.Utility.PolarPoint(varP0, PI / -2 + Ang1, dblW)
                Dist1 = GetDistance(varP0, varP1)
                varP4 = ThisDrawing.Utility.PolarPoint(varP0, Ang1, Dist1 / 2)
                varP4 = ThisDrawing.Utility.PolarPoint(varP4, Ang1 + PI / 2, 5)
                varP5 = ThisDrawing.Utility.PolarPoint(varP4, PI / 2 + Ang1, 2)
                adblCoordinate(0) = varP0(0)
                adblCoordinate(1) = varP0(1)
                adblCoordinate(2) = varP1(0)
                adblCoordinate(3) = varP1(1)
                adblCoordinate(4) = varP2(0)
                adblCoordinate(5) = varP2(1)
                adblCoordinate(6) = varP3(0)
                adblCoordinate(7) = varP3(1)
   
                Set objAddLightWeightPolyline = ThisDrawing.ModelSpace.AddLightWeightPolyline(adblCoordinate)
                objAddLightWeightPolyline.Closed = True
                objAddLightWeightPolyline.Layer = "JBEAM"
                objAddLightWeightPolyline.Update
                Set objText1 = ThisDrawing.ModelSpace.AddText(strN + CStr(intNum) + "(" + txtW + ")", varP4, 40)
                objText1.Layer = "JBEAMT"
                objText1.StyleName = "C40"
                objText1.ScaleFactor = 0.7
                objText1.Alignment = acAlignmentBottomCenter
                objText1.TextAlignmentPoint = varP4
                objText1.Rotate varP4, Ang1
                objText1.Update
                intNum = intNum + 1
                Me.txtNum = intNum
            Loop
        End If
    Else
        If chkUp.Value = True Then
            Do While Err.Number = 0
                On Error GoTo Z
                varP0 = ThisDrawing.Utility.GetPoint(, "點1")
                varP1 = ThisDrawing.Utility.GetPoint(varP0, "點2")
                Ang1 = ThisDrawing.Utility.AngleFromXAxis(varP0, varP1)
                varP2 = ThisDrawing.Utility.PolarPoint(varP1, PI / 2 + Ang1, dblW)
                varP3 = ThisDrawing.Utility.PolarPoint(varP0, PI / 2 + Ang1, dblW)
                Dist1 = GetDistance(varP0, varP1)
                varP4 = ThisDrawing.Utility.PolarPoint(varP3, Ang1, Dist1 / 2)
                varP4 = ThisDrawing.Utility.PolarPoint(varP4, Ang1 + PI / 2, 5)
                adblCoordinate(0) = varP0(0)
                adblCoordinate(1) = varP0(1)
                adblCoordinate(2) = varP1(0)
                adblCoordinate(3) = varP1(1)
                adblCoordinate(4) = varP2(0)
                adblCoordinate(5) = varP2(1)
                adblCoordinate(6) = varP3(0)
                adblCoordinate(7) = varP3(1)
   
                Set objAddLightWeightPolyline = ThisDrawing.ModelSpace.AddLightWeightPolyline(adblCoordinate)
                objAddLightWeightPolyline.Closed = True
                objAddLightWeightPolyline.Layer = "JBEAM"
                objAddLightWeightPolyline.Update
                Set objText1 = ThisDrawing.ModelSpace.AddText(strN + CStr(intNum) + "(" + txtW + ")", varP4, 40)
                objText1.Layer = "JBEAMT"
                objText1.StyleName = "C40"
                objText1.ScaleFactor = 0.7
                objText1.Alignment = acAlignmentBottomCenter
                objText1.TextAlignmentPoint = varP4
                objText1.Rotate varP4, Ang1
                objText1.Update
            Loop
        ElseIf chkMiddle.Value = True Then
            Do While Err.Number = 0
                On Error GoTo Z
                varP0 = ThisDrawing.Utility.GetPoint(, "點1")
                varP1 = ThisDrawing.Utility.GetPoint(varP0, "點2")
                Ang1 = ThisDrawing.Utility.AngleFromXAxis(varP0, varP1)
                varP2 = ThisDrawing.Utility.PolarPoint(varP1, PI / 2 + Ang1, dblW / 2)
                varP3 = ThisDrawing.Utility.PolarPoint(varP0, PI / 2 + Ang1, dblW / 2)
                varP22 = ThisDrawing.Utility.PolarPoint(varP1, PI / -2 + Ang1, dblW / 2)
                varP33 = ThisDrawing.Utility.PolarPoint(varP0, PI / -2 + Ang1, dblW / 2)
                Dist1 = GetDistance(varP0, varP1)
                varP4 = ThisDrawing.Utility.PolarPoint(varP3, Ang1, Dist1 / 2)
                varP4 = ThisDrawing.Utility.PolarPoint(varP4, Ang1 + PI / 2, 5)
                varP5 = ThisDrawing.Utility.PolarPoint(varP4, PI / 2 + Ang1, 2)
                adblCoordinate(0) = varP33(0)
                adblCoordinate(1) = varP33(1)
                adblCoordinate(2) = varP22(0)
                adblCoordinate(3) = varP22(1)
                adblCoordinate(4) = varP2(0)
                adblCoordinate(5) = varP2(1)
                adblCoordinate(6) = varP3(0)
                adblCoordinate(7) = varP3(1)
   
                Set objAddLightWeightPolyline = ThisDrawing.ModelSpace.AddLightWeightPolyline(adblCoordinate)
                objAddLightWeightPolyline.Closed = True
                objAddLightWeightPolyline.Layer = "JBEAM"
                objAddLightWeightPolyline.Update
                Set objText1 = ThisDrawing.ModelSpace.AddText(strN + CStr(intNum) + "(" + txtW + ")", varP4, 40)
                objText1.StyleName = "C40"
                objText1.Layer = "JBEAMT"
                objText1.ScaleFactor = 0.7
                objText1.Alignment = acAlignmentBottomCenter
                objText1.TextAlignmentPoint = varP4
                objText1.Rotate varP4, Ang1
                objText1.Update
            Loop
        ElseIf chkDown.Value = True Then
            Do While Err.Number = 0
                On Error GoTo Z
                varP0 = ThisDrawing.Utility.GetPoint(, "點1")
                varP1 = ThisDrawing.Utility.GetPoint(varP0, "點2")
                Ang1 = ThisDrawing.Utility.AngleFromXAxis(varP0, varP1)
                varP2 = ThisDrawing.Utility.PolarPoint(varP1, PI / -2 + Ang1, dblW)
                varP3 = ThisDrawing.Utility.PolarPoint(varP0, PI / -2 + Ang1, dblW)
                Dist1 = GetDistance(varP0, varP1)
                varP4 = ThisDrawing.Utility.PolarPoint(varP0, Ang1, Dist1 / 2)
                varP4 = ThisDrawing.Utility.PolarPoint(varP4, Ang1 + PI / 2, 5)
                varP5 = ThisDrawing.Utility.PolarPoint(varP4, PI / 2 + Ang1, 2)
                adblCoordinate(0) = varP0(0)
                adblCoordinate(1) = varP0(1)
                adblCoordinate(2) = varP1(0)
                adblCoordinate(3) = varP1(1)
                adblCoordinate(4) = varP2(0)
                adblCoordinate(5) = varP2(1)
                adblCoordinate(6) = varP3(0)
                adblCoordinate(7) = varP3(1)
   
                Set objAddLightWeightPolyline = ThisDrawing.ModelSpace.AddLightWeightPolyline(adblCoordinate)
                objAddLightWeightPolyline.Closed = True
                objAddLightWeightPolyline.Layer = "JBEAM"
                objAddLightWeightPolyline.Update
                Set objText1 = ThisDrawing.ModelSpace.AddText(strN + CStr(intNum) + "(" + txtW + ")", varP4, 40)
                objText1.Layer = "JBEAMT"
                objText1.StyleName = "C40"
                objText1.ScaleFactor = 0.7
                objText1.Alignment = acAlignmentBottomCenter
                objText1.TextAlignmentPoint = varP4
                objText1.Rotate varP4, Ang1
                objText1.Update
            Loop
        End If

    End If
Z:
    Me.show
End Sub

Attribute VB_Name = "RCPanel"
Attribute VB_Base = "0{F5B44C66-7A4F-4468-9A17-906E171C945E}{41972510-FCED-448C-9C78-AD471B096C8D}"
Attribute VB_GlobalNameSpace = False
Attribute VB_Creatable = False
Attribute VB_PredeclaredId = True
Attribute VB_Exposed = False
Attribute VB_TemplateDerived = False
Attribute VB_Customizable = False
Private Sub cmdCancel_Click()
    Me.Hide
    BasicForm.show
End Sub



Private Sub cmdDraw_Click()
    Dim strN, strNN As String
    Dim intNum As Integer
    Dim objLine As AcadLine
    Dim varP0, varP1, varP2, varP3 As Variant
    Dim LineCo(0 To 3) As Double
    Dim objText As AcadText
    
    Me.Hide
    Call CreateLayer("SLABT", 7, "CONTINUOUS")
    strN = Me.txtN
    strNN = Me.txtNN
    intNum = Val(Me.txtNum)
    On Error GoTo Z
    If Me.chkContinue.Value = True Then
        Do While Err.Number = 0
            varP0 = ThisDrawing.Utility.GetPoint(, "插入點")
            If Me.chkFagi.Value = True Then
                Set objText = ThisDrawing.ModelSpace.AddText("FS" + CStr(intNum), varP0, 40)
                objText.StyleName = "C40"
                objText.Alignment = acAlignmentBottomCenter
                objText.ScaleFactor = 0.7
                objText.TextAlignmentPoint = varP0
                objText.Layer = "SLABT"
                varP1 = ThisDrawing.Utility.PolarPoint(varP0, PI / 2, 45)
                varP2 = ThisDrawing.Utility.PolarPoint(varP1, PI, 40)
                varP3 = ThisDrawing.Utility.PolarPoint(varP1, 0, 40)
                varP1 = ThisDrawing.Utility.PolarPoint(varP1, PI / 2, 5)
                Set objText = ThisDrawing.ModelSpace.AddText(strN + CStr(intNum) + strNN, varP1, 40)
                objText.StyleName = "C40"
                objText.Alignment = acAlignmentBottomCenter
                objText.ScaleFactor = 0.7
                objText.TextAlignmentPoint = varP1
                objText.Layer = "SLABT"
                Set objLine = ThisDrawing.ModelSpace.AddLine(varP2, varP3)
                objLine.Layer = "SLABT"
                intNum = intNum + 1
                Me.txtNum = CStr(intNum)
                ThisDrawing.Application.Update
            Else
                Set objText = ThisDrawing.ModelSpace.AddText(strN + CStr(intNum) + strNN, varP0, 40)
                objText.StyleName = "C40"
                objText.Alignment = acAlignmentBottomCenter
                objText.ScaleFactor = 0.7
                objText.TextAlignmentPoint = varP0
                objText.Layer = "SLABT"
                ThisDrawing.Application.Update
                intNum = intNum + 1
                Me.txtNum = CStr(intNum)
            End If
        Loop
    Else
        Do While Err.Number = 0
            varP0 = ThisDrawing.Utility.GetPoint(, "插入點")
            If Me.chkFagi.Value = True Then
                Set objText = ThisDrawing.ModelSpace.AddText("FS" + CStr(intNum), varP0, 40)
                objText.StyleName = "C40"
                objText.Alignment = acAlignmentBottomCenter
                objText.ScaleFactor = 0.7
                objText.TextAlignmentPoint = varP0
                objText.Layer = "SLABT"
                varP1 = ThisDrawing.Utility.PolarPoint(varP0, PI / 2, 45)
                varP2 = ThisDrawing.Utility.PolarPoint(varP1, PI, 40)
                varP3 = ThisDrawing.Utility.PolarPoint(varP1, 0, 40)
                varP1 = ThisDrawing.Utility.PolarPoint(varP1, PI / 2, 5)
                Set objText = ThisDrawing.ModelSpace.AddText(strN + CStr(intNum) + strNN, varP1, 40)
                objText.StyleName = "C40"
                objText.Alignment = acAlignmentBottomCenter
                objText.ScaleFactor = 0.7
                objText.TextAlignmentPoint = varP1
                objText.Layer = "SLABT"
                Set objLine = ThisDrawing.ModelSpace.AddLine(varP2, varP3)
                objLine.Layer = "SLABT"
                ThisDrawing.Application.Update
            Else
                Set objText = ThisDrawing.ModelSpace.AddText(strN + CStr(intNum) + strNN, varP0, 40)
                objText.StyleName = "C40"
                objText.Alignment = acAlignmentBottomCenter
                objText.ScaleFactor = 0.7
                objText.TextAlignmentPoint = varP0
                objText.Layer = "SLABT"
                ThisDrawing.Application.Update
            End If
        Loop
    End If
Z:
    Me.show
End Sub

Attribute VB_Name = "RCPillar"
Attribute VB_Base = "0{DCD57400-F895-41CC-B148-F3AE3EB4BDEC}{9938EB96-F0C1-40FE-B0FC-E196B9E2F6EA}"
Attribute VB_GlobalNameSpace = False
Attribute VB_Creatable = False
Attribute VB_PredeclaredId = True
Attribute VB_Exposed = False
Attribute VB_TemplateDerived = False
Attribute VB_Customizable = False
Private Sub cmdCancel_Click()
    Me.Hide
    BasicForm.show
End Sub

Private Sub cmdDraw_Click()
    Dim varP0 As Variant
    Dim varP1, varP2, varP3, varP4, varP5, varP6, varP7 As Variant
    Dim LwpLine1 As AcadLWPolyline
    Dim intNum As Integer
    Dim strN As String
    Dim objText1 As AcadText
    Dim objText2 As AcadText
    Dim Dist1, Ang1, Dist2, Dist3 As Double
    Dim arrayCor(0 To 7) As Double

    Me.Hide
    Call CreateLayer("COL", 2, "CONTINUOUS")
    Call CreateLayer("COLT", 1, "CONTINUOUS")
    Call CreateLayer("COLS", 1, "CONTINUOUS")
    intNum = Me.txtNum
    strN = Me.txtN
    If Me.chkRotate.Value = True Then
    If Me.chkContinue = True Then
        Do While Err.Number = 0
            On Error GoTo Z
            varP0 = ThisDrawing.Utility.GetPoint(, "點1")
            varP1 = ThisDrawing.Utility.GetPoint(varP0, "旋轉角度")
            varP5 = ThisDrawing.Utility.GetPoint(varP1, "點2")
            Ang1 = ThisDrawing.Utility.AngleFromXAxis(varP0, varP1)
            varP2 = ThisDrawing.Utility.PolarPoint(varP1, PI / -2, 60)
            Dist1 = GetDistance(varP1, varP5)
            Dist2 = Round(GetDistance(varP0, varP1), 0)
            Dist3 = Round(GetDistance(varP1, varP5), 0)
            varP6 = ThisDrawing.Utility.PolarPoint(varP1, PI / 2 + Ang1, Dist1)
            varP4 = ThisDrawing.Utility.PolarPoint(varP0, PI / 2 + Ang1, Dist1)
            Dist3 = Round(GetDistance(varP1, varP6), 0)
            arrayCor(0) = varP0(0):            arrayCor(1) = varP0(1)
            arrayCor(2) = varP1(0):            arrayCor(3) = varP1(1)
            arrayCor(4) = varP6(0):            arrayCor(5) = varP6(1)
            arrayCor(6) = varP4(0):            arrayCor(7) = varP4(1)
            Set LwpLine1 = ThisDrawing.ModelSpace.AddLightWeightPolyline(arrayCor)
            LwpLine1.Layer = "COL"
            LwpLine1.Closed = True
            LwpLine1.Update
            Set objText1 = ThisDrawing.ModelSpace.AddText(strN + CStr(intNum), varP2, 40)
            objText1.Layer = "COLT"
            objText1.StyleName = "C40"
            objText1.ScaleFactor = 0.7
            objText1.Alignment = acAlignmentBottomLeft
            objText1.TextAlignmentPoint = varP2
            objText1.Update
            varP7 = ThisDrawing.Utility.PolarPoint(varP2, PI / -2, 50)
            Set objText2 = ThisDrawing.ModelSpace.AddText("(" + CStr(Dist2) + "x" + CStr(Dist3) + ")", varP7, 40)
            objText2.Layer = "COLS"
            objText2.StyleName = "C40"
            objText2.ScaleFactor = 0.7
            objText2.Alignment = acAlignmentBottomLeft
            objText2.TextAlignmentPoint = varP7
            objText2.Update
            intNum = intNum + 1
            Me.txtNum = CStr(intNum)
    Loop
    Else
    Do While Err.Number = 0
            On Error GoTo Z
            varP0 = ThisDrawing.Utility.GetPoint(, "點1")
            varP1 = ThisDrawing.Utility.GetPoint(varP0, "旋轉角度")
            varP5 = ThisDrawing.Utility.GetPoint(varP1, "點2")
            Ang1 = ThisDrawing.Utility.AngleFromXAxis(varP0, varP1)
            varP2 = ThisDrawing.Utility.PolarPoint(varP1, PI / -2, 60)
            If intNum < 10 Then
                varP3 = ThisDrawing.Utility.PolarPoint(varP2, PI, 30)
            ElseIf intNum < 100 Then
                varP3 = ThisDrawing.Utility.PolarPoint(varP2, PI, 40)
            Else
                varP3 = ThisDrawing.Utility.PolarPoint(varP2, PI, 50)
            End If
            Dist1 = GetDistance(varP1, varP5)
            Dist2 = Round(GetDistance(varP0, varP1), 0)
            Dist3 = Round(GetDistance(varP1, varP5), 0)
            varP6 = ThisDrawing.Utility.PolarPoint(varP1, PI / 2 + Ang1, Dist1)
            varP4 = ThisDrawing.Utility.PolarPoint(varP0, PI / 2 + Ang1, Dist1)
            Dist3 = Round(GetDistance(varP1, varP6), 0)
            arrayCor(0) = varP0(0)
            arrayCor(1) = varP0(1)
            arrayCor(2) = varP1(0)
            arrayCor(3) = varP1(1)
            arrayCor(4) = varP6(0)
            arrayCor(5) = varP6(1)
            arrayCor(6) = varP4(0)
            arrayCor(7) = varP4(1)
            Set LwpLine1 = ThisDrawing.ModelSpace.AddLightWeightPolyline(arrayCor)
            LwpLine1.Layer = "COL"
            LwpLine1.Closed = True
            LwpLine1.Update
            Set objText1 = ThisDrawing.ModelSpace.AddText(strN + CStr(intNum), varP2, 40)
            objText1.Layer = "COLT"
            objText1.StyleName = "C40"
            objText1.ScaleFactor = 0.7
            objText1.Alignment = acAlignmentBottomLeft
            objText1.TextAlignmentPoint = varP2
            objText1.Update
            varP7 = ThisDrawing.Utility.PolarPoint(varP2, PI / -2, 50)
            Set objText2 = ThisDrawing.ModelSpace.AddText("(" + CStr(Dist2) + "x" + CStr(Dist3) + ")", varP2, 40)
            objText2.Layer = "COLS"
            objText2.StyleName = "C40"
            objText2.ScaleFactor = 0.7
            objText2.Alignment = acAlignmentBottomLeft
            objText2.TextAlignmentPoint = varP7
            objText2.Update
Loop
    GoTo Z
    End If
    Else
    If Me.chkContinue = True Then
        Do While Err.Number = 0
            On Error GoTo Z
            varP0 = ThisDrawing.Utility.GetPoint(, "點1")
            varP1 = ThisDrawing.Utility.GetCorner(varP0, "點2")
            varP2 = ThisDrawing.Utility.PolarPoint(varP0, PI / -2, 60)
            If intNum < 10 Then
                varP3 = ThisDrawing.Utility.PolarPoint(varP2, PI, 30)
            ElseIf intNum < 100 Then
                varP3 = ThisDrawing.Utility.PolarPoint(varP2, PI, 40)
            Else
                varP3 = ThisDrawing.Utility.PolarPoint(varP2, PI, 50)
            End If
            Dist1 = GetDistance(varP0, varP1)
            Ang1 = ThisDrawing.Utility.AngleFromXAxis(varP0, varP1)
            Dist2 = Round(Dist1 * Cos(Ang1), 0)
            Dist3 = Round(Dist1 * Sin(Ang1), 0)
            Set LwpLine1 = DrawRectangle(varP0, varP1)
            LwpLine1.Layer = "COL"
            LwpLine1.Update
            varP2 = ThisDrawing.Utility.PolarPoint(varP2, 0, Dist2)
            varP7 = ThisDrawing.Utility.PolarPoint(varP2, PI / -2, 50)
            Set objText1 = ThisDrawing.ModelSpace.AddText(strN + CStr(intNum), varP2, 40)
            objText1.Layer = "COLT"
            objText1.StyleName = "C40"
            objText1.ScaleFactor = 0.7
            objText1.Alignment = acAlignmentBottomLeft
            objText1.TextAlignmentPoint = varP2
            objText1.Update
            Set objText2 = ThisDrawing.ModelSpace.AddText("(" + CStr(Dist2) + "x" + CStr(Dist3) + ")", varP7, 40)
            objText2.Layer = "COLS"
            objText2.StyleName = "C40"
            objText2.ScaleFactor = 0.7
            objText2.Alignment = acAlignmentBottomLeft
            objText2.TextAlignmentPoint = varP7
            objText2.Update
            intNum = intNum + 1
            Me.txtNum = CStr(intNum)
    Loop
    Else
    Do While Err.Number = 0
        On Error GoTo Z
        varP0 = ThisDrawing.Utility.GetPoint(, "點1")
        varP1 = ThisDrawing.Utility.GetCorner(varP0, "點2")
        varP2 = ThisDrawing.Utility.PolarPoint(varP0, PI / -2, 60)
        If intNum < 10 Then
            varP3 = ThisDrawing.Utility.PolarPoint(varP2, PI, 30)
        ElseIf intNum < 100 Then
            varP3 = ThisDrawing.Utility.PolarPoint(varP2, PI, 40)
        Else
            varP3 = ThisDrawing.Utility.PolarPoint(varP2, PI, 50)
        End If
        Dist1 = GetDistance(varP0, varP1)
        Ang1 = ThisDrawing.Utility.AngleFromXAxis(varP0, varP1)
        Dist2 = Round(Dist1 * Cos(Ang1), 0)
        Dist3 = Round(Dist1 * Sin(Ang1), 0)
        Set LwpLine1 = DrawRectangle(varP0, varP1)
        LwpLine1.Layer = "col"
        LwpLine1.Update
        varP2 = ThisDrawing.Utility.PolarPoint(varP2, 0, Dist2)
        varP7 = ThisDrawing.Utility.PolarPoint(varP2, PI / -2, 50)
        Set objText1 = ThisDrawing.ModelSpace.AddText(strN + CStr(intNum), varP2, 40)
        objText1.Layer = "COLT"
        objText1.StyleName = "C40"
        objText1.ScaleFactor = 0.7
        objText1.Alignment = acAlignmentBottomLeft
        objText1.TextAlignmentPoint = varP2
        objText1.Update
        Set objText2 = ThisDrawing.ModelSpace.AddText("(" + CStr(Dist2) + "x" + CStr(Dist3) + ")", varP7, 40)
        objText2.Layer = "COLS"
        objText2.StyleName = "C40"
        objText2.ScaleFactor = 0.7
        objText2.Alignment = acAlignmentBottomLeft
        objText2.TextAlignmentPoint = varP7
        objText2.Update
    Loop
    GoTo Z
    End If
    End If
Z:
    Me.show
End Sub

Attribute VB_Name = "SSBeams"
Attribute VB_Base = "0{391ECFF1-DEB2-4042-9E2A-6C8F6D4969C5}{2FA45A8E-4C1D-443B-AE70-FB0185CD9FBA}"
Attribute VB_GlobalNameSpace = False
Attribute VB_Creatable = False
Attribute VB_PredeclaredId = True
Attribute VB_Exposed = False
Attribute VB_TemplateDerived = False
Attribute VB_Customizable = False
Private Sub chkDown_Click()
    If Me.chkDown.Value = True Then
        Me.chkUp.Value = False
        Me.chkMiddle.Value = False
    End If
End Sub

Private Sub chkMiddle_Click()
    If Me.chkMiddle.Value = True Then
        Me.chkUp.Value = False
        Me.chkDown.Value = False
    End If
End Sub

Private Sub chkUp_Click()
    If Me.chkUp.Value = True Then
        Me.chkMiddle.Value = False
        Me.chkDown.Value = False
    End If
End Sub

Private Sub cmdCancel_Click()
    Me.Hide
    BasicForm.show
End Sub

Private Sub cmdDrawing_Click()
    Dim varP0, varP1, varP2, varP3, varP4, varP5, varP6, varP7, varP8, varP9, varP10, varP11, varP12 As Variant
    Dim LwpLine1 As AcadLWPolyline
    Dim Dist1, Ang1, Ang2, dblW As Double
    Dim Rect1(0 To 7) As Double
    Dim Tra1(0 To 5) As Double
    Dim objHat As AcadHatch
    Dim patternName As String
    Dim PatternType As Long
    Dim bAssociativity As Boolean
    Dim outerLoop(0 To 0) As AcadEntity
    Dim objText As AcadText
    Dim strN As String
    Dim intNum As Integer
    
    Me.Hide
    Call CreateLayer("SB", 1, "CONTINUOUS")
    Call CreateLayer("BEAMT", 3, "CONTINUOUS")
    patternName = "ANSI31"
    PatternType = 0
    bAssociativity = True
    dblW = Val(Me.txtW)
    strN = Me.txtN
    intNum = Val(Me.txtNum)
    If Me.chkContinue = True Then
        Do While Err.Number = 0
            On Error GoTo Z
            If chkUp.Value = True Then
                With ThisDrawing.Utility
                    varP0 = .GetPoint(, "P1")
                    varP1 = .GetPoint(varP0, "P2")
                    Dist1 = GetDistance(varP0, varP1)
                    Ang1 = .AngleFromXAxis(varP0, varP1)
                    varP2 = .PolarPoint(varP0, Ang1, 20)
                    varP3 = .PolarPoint(varP1, Ang1, -20)
                    varP4 = .PolarPoint(varP3, PI / 2 + Ang1, dblW / 2)
                    varP5 = .PolarPoint(varP3, PI / 2 + Ang1, dblW)
                    varP6 = .PolarPoint(varP2, PI / 2 + Ang1, dblW / 2)
                    varP7 = .PolarPoint(varP2, PI / 2 + Ang1, dblW)
                    varP8 = .PolarPoint(varP0, PI / 2 + Ang1, (dblW - 20) / 2)
                    varP9 = .PolarPoint(varP0, PI / 2 + Ang1, (dblW - 20) / 2 + 20)
                    varP10 = .PolarPoint(varP1, PI / 2 + Ang1, (dblW - 20) / 2)
                    varP11 = .PolarPoint(varP1, PI / 2 + Ang1, (dblW - 20) / 2 + 20)
                    varP12 = .PolarPoint(varP7, Ang1, Dist1 / 2 - 20)
                    varP12 = .PolarPoint(varP12, Ang1 + PI / 2, 5)
                End With
                Rect1(0) = varP2(0): Rect1(1) = varP2(1)
                Rect1(2) = varP3(0): Rect1(3) = varP3(1)
                Rect1(4) = varP5(0): Rect1(5) = varP5(1)
                Rect1(6) = varP7(0): Rect1(7) = varP7(1)
                Set LwpLine1 = ThisDrawing.ModelSpace.AddLightWeightPolyline(Rect1)
                LwpLine1.Closed = True
                LwpLine1.Layer = "SB"
                LwpLine1.Update
                Set objText = ThisDrawing.ModelSpace.AddText(txtN + CStr(intNum) + "(" + txtW + ")", varP12, 40)
                objText.Alignment = acAlignmentBottomCenter
                objText.Layer = "BEAMT"
                objText.ScaleFactor = 0.7
                objText.StyleName = "C40"
                objText.TextAlignmentPoint = varP12
                objText.Rotate varP12, Ang1
                Tra1(0) = varP8(0): Tra1(1) = varP8(1)
                Tra1(2) = varP6(0): Tra1(3) = varP6(1)
                Tra1(4) = varP9(0): Tra1(5) = varP9(1)
                Set LwpLine1 = ThisDrawing.ModelSpace.AddLightWeightPolyline(Tra1)
                LwpLine1.Closed = True
                LwpLine1.Color = acYellow
                LwpLine1.Layer = "SB"
                LwpLine1.Update
                ' Create the associative Hatch object
                Set objHat = ThisDrawing.ModelSpace.AddHatch(PatternType, patternName, bAssociativity)

                ' Create the outer boundary for the hatch
                Set outerLoop(0) = LwpLine1
                objHat.AppendOuterLoop (outerLoop)
                objHat.Layer = "SB"
                objHat.Color = acYellow
                objHat.Update
                Tra1(0) = varP4(0): Tra1(1) = varP4(1)
                Tra1(2) = varP10(0): Tra1(3) = varP10(1)
                Tra1(4) = varP11(0): Tra1(5) = varP11(1)
                Set LwpLine1 = ThisDrawing.ModelSpace.AddLightWeightPolyline(Tra1)
                LwpLine1.Closed = True
                LwpLine1.Color = acYellow
                LwpLine1.Layer = "SB"
                LwpLine1.Update
                ' Create the associative Hatch object
                Set objHat = ThisDrawing.ModelSpace.AddHatch(PatternType, patternName, bAssociativity)

                ' Create the outer boundary for the hatch
                Set outerLoop(0) = LwpLine1
                objHat.AppendOuterLoop (outerLoop)
                objHat.Layer = "SB"
                objHat.Color = acYellow
                objHat.Update
            ElseIf chkMiddle.Value = True Then
                With ThisDrawing.Utility
                    varP0 = .GetPoint(, "P1")
                    varP1 = .GetPoint(varP0, "P2")
                    Dist1 = GetDistance(varP0, varP1)
                    Ang1 = .AngleFromXAxis(varP0, varP1)
                    varP2 = .PolarPoint(varP0, Ang1, 20)
                    varP3 = .PolarPoint(varP1, Ang1, -20)
                    varP4 = .PolarPoint(varP3, PI / 2 + Ang1, dblW / 2)
                    varP5 = .PolarPoint(varP3, PI / 2 + Ang1, dblW)
                    varP6 = .PolarPoint(varP2, PI / 2 + Ang1, dblW / 2)
                    varP7 = .PolarPoint(varP2, PI / 2 + Ang1, dblW)
                    varP8 = .PolarPoint(varP0, PI / 2 + Ang1, (dblW - 20) / 2)
                    varP9 = .PolarPoint(varP0, PI / 2 + Ang1, (dblW - 20) / 2 + 20)
                    varP10 = .PolarPoint(varP1, PI / 2 + Ang1, (dblW - 20) / 2)
                    varP11 = .PolarPoint(varP1, PI / 2 + Ang1, (dblW - 20) / 2 + 20)
                    varP12 = .PolarPoint(varP7, Ang1, Dist1 / 2 - 20)
                    varP12 = .PolarPoint(varP12, Ang1 + PI / 2, 5)
                End With
                Rect1(0) = varP2(0): Rect1(1) = varP2(1)
                Rect1(2) = varP3(0): Rect1(3) = varP3(1)
                Rect1(4) = varP5(0): Rect1(5) = varP5(1)
                Rect1(6) = varP7(0): Rect1(7) = varP7(1)
                Set LwpLine1 = ThisDrawing.ModelSpace.AddLightWeightPolyline(Rect1)
                LwpLine1.Closed = True
                LwpLine1.Layer = "SB"
                LwpLine1.Move varP6, varP2
                LwpLine1.Update
                Set objText = ThisDrawing.ModelSpace.AddText(txtN + CStr(intNum) + "(" + txtW + ")", varP12, 40)
                objText.Alignment = acAlignmentBottomCenter
                objText.Layer = "BEAMT"
                objText.ScaleFactor = 0.7
                objText.StyleName = "C40"
                objText.TextAlignmentPoint = varP12
                objText.Rotate varP12, Ang1
                objText.Move varP6, varP2
                objText.Update
                Tra1(0) = varP8(0): Tra1(1) = varP8(1)
                Tra1(2) = varP6(0): Tra1(3) = varP6(1)
                Tra1(4) = varP9(0): Tra1(5) = varP9(1)
                Set LwpLine1 = ThisDrawing.ModelSpace.AddLightWeightPolyline(Tra1)
                LwpLine1.Closed = True
                LwpLine1.Color = acYellow
                LwpLine1.Layer = "SB"
                LwpLine1.Move varP6, varP2
                LwpLine1.Update
                ' Create the associative Hatch object
                Set objHat = ThisDrawing.ModelSpace.AddHatch(PatternType, patternName, bAssociativity)

                ' Create the outer boundary for the hatch
                Set outerLoop(0) = LwpLine1
                objHat.AppendOuterLoop (outerLoop)
                objHat.Layer = "SB"
                objHat.Color = acYellow
                objHat.Update
                Tra1(0) = varP4(0): Tra1(1) = varP4(1)
                Tra1(2) = varP10(0): Tra1(3) = varP10(1)
                Tra1(4) = varP11(0): Tra1(5) = varP11(1)
                Set LwpLine1 = ThisDrawing.ModelSpace.AddLightWeightPolyline(Tra1)
                LwpLine1.Closed = True
                LwpLine1.Color = acYellow
                LwpLine1.Layer = "SB"
                LwpLine1.Move varP6, varP2
                LwpLine1.Update
                ' Create the associative Hatch object
                Set objHat = ThisDrawing.ModelSpace.AddHatch(PatternType, patternName, bAssociativity)

                ' Create the outer boundary for the hatch
                Set outerLoop(0) = LwpLine1
                objHat.AppendOuterLoop (outerLoop)
                objHat.Layer = "SB"
                objHat.Color = acYellow
                objHat.Update
            ElseIf chkDown.Value = True Then
                With ThisDrawing.Utility
                    varP0 = .GetPoint(, "P1")
                    varP1 = .GetPoint(varP0, "P2")
                    Dist1 = GetDistance(varP0, varP1)
                    Ang1 = .AngleFromXAxis(varP0, varP1)
                    varP2 = .PolarPoint(varP0, Ang1, 20)
                    varP3 = .PolarPoint(varP1, Ang1, -20)
                    varP4 = .PolarPoint(varP3, PI / 2 + Ang1, dblW / 2)
                    varP5 = .PolarPoint(varP3, PI / 2 + Ang1, dblW)
                    varP6 = .PolarPoint(varP2, PI / 2 + Ang1, dblW / 2)
                    varP7 = .PolarPoint(varP2, PI / 2 + Ang1, dblW)
                    varP8 = .PolarPoint(varP0, PI / 2 + Ang1, (dblW - 20) / 2)
                    varP9 = .PolarPoint(varP0, PI / 2 + Ang1, (dblW - 20) / 2 + 20)
                    varP10 = .PolarPoint(varP1, PI / 2 + Ang1, (dblW - 20) / 2)
                    varP11 = .PolarPoint(varP1, PI / 2 + Ang1, (dblW - 20) / 2 + 20)
                    varP12 = .PolarPoint(varP7, Ang1, Dist1 / 2 - 20)
                    varP12 = .PolarPoint(varP12, Ang1 + PI / 2, 5)
                End With
                Rect1(0) = varP2(0): Rect1(1) = varP2(1)
                Rect1(2) = varP3(0): Rect1(3) = varP3(1)
                Rect1(4) = varP5(0): Rect1(5) = varP5(1)
                Rect1(6) = varP7(0): Rect1(7) = varP7(1)
                Set LwpLine1 = ThisDrawing.ModelSpace.AddLightWeightPolyline(Rect1)
                LwpLine1.Closed = True
                LwpLine1.Layer = "SB"
                LwpLine1.Move varP7, varP2
                LwpLine1.Update
                Set objText = ThisDrawing.ModelSpace.AddText(txtN + CStr(intNum) + "(" + txtW + ")", varP12, 40)
                objText.Alignment = acAlignmentBottomCenter
                objText.ScaleFactor = 0.7
                objText.Layer = "BEAMT"
                objText.StyleName = "C40"
                objText.TextAlignmentPoint = varP12
                objText.Rotate varP12, Ang1
                objText.Move varP7, varP2
                objText.Update
                Tra1(0) = varP8(0): Tra1(1) = varP8(1)
                Tra1(2) = varP6(0): Tra1(3) = varP6(1)
                Tra1(4) = varP9(0): Tra1(5) = varP9(1)
                Set LwpLine1 = ThisDrawing.ModelSpace.AddLightWeightPolyline(Tra1)
                LwpLine1.Closed = True
                LwpLine1.Color = acYellow
                LwpLine1.Layer = "SB"
                LwpLine1.Move varP7, varP2
                LwpLine1.Update
                ' Create the associative Hatch object
                Set objHat = ThisDrawing.ModelSpace.AddHatch(PatternType, patternName, bAssociativity)

                ' Create the outer boundary for the hatch
                Set outerLoop(0) = LwpLine1
                objHat.AppendOuterLoop (outerLoop)
                objHat.Layer = "SB"
                objHat.Color = acYellow
                objHat.Update
                Tra1(0) = varP4(0): Tra1(1) = varP4(1)
                Tra1(2) = varP10(0): Tra1(3) = varP10(1)
                Tra1(4) = varP11(0): Tra1(5) = varP11(1)
                Set LwpLine1 = ThisDrawing.ModelSpace.AddLightWeightPolyline(Tra1)
                LwpLine1.Closed = True
                LwpLine1.Color = acYellow
                LwpLine1.Layer = "SB"
                LwpLine1.Move varP7, varP2
                LwpLine1.Update
                ' Create the associative Hatch object
                Set objHat = ThisDrawing.ModelSpace.AddHatch(PatternType, patternName, bAssociativity)

                ' Create the outer boundary for the hatch
                Set outerLoop(0) = LwpLine1
                objHat.AppendOuterLoop (outerLoop)
                objHat.Layer = "SB"
                objHat.Color = acYellow
                objHat.Update
            End If
            intNum = intNum + 1
    Loop
    Else
    Do While Err.Number = 0
            On Error GoTo Z
            If chkUp.Value = True Then
                With ThisDrawing.Utility
                    varP0 = .GetPoint(, "P1")
                    varP1 = .GetPoint(varP0, "P2")
                    Dist1 = GetDistance(varP0, varP1)
                    Ang1 = .AngleFromXAxis(varP0, varP1)
                    varP2 = .PolarPoint(varP0, Ang1, 20)
                    varP3 = .PolarPoint(varP1, Ang1, -20)
                    varP4 = .PolarPoint(varP3, PI / 2 + Ang1, dblW / 2)
                    varP5 = .PolarPoint(varP3, PI / 2 + Ang1, dblW)
                    varP6 = .PolarPoint(varP2, PI / 2 + Ang1, dblW / 2)
                    varP7 = .PolarPoint(varP2, PI / 2 + Ang1, dblW)
                    varP8 = .PolarPoint(varP0, PI / 2 + Ang1, (dblW - 20) / 2)
                    varP9 = .PolarPoint(varP0, PI / 2 + Ang1, (dblW - 20) / 2 + 20)
                    varP10 = .PolarPoint(varP1, PI / 2 + Ang1, (dblW - 20) / 2)
                    varP11 = .PolarPoint(varP1, PI / 2 + Ang1, (dblW - 20) / 2 + 20)
                    varP12 = .PolarPoint(varP7, Ang1, Dist1 / 2 - 20)
                    varP12 = .PolarPoint(varP12, Ang1 + PI / 2, 5)
                End With
                Rect1(0) = varP2(0): Rect1(1) = varP2(1)
                Rect1(2) = varP3(0): Rect1(3) = varP3(1)
                Rect1(4) = varP5(0): Rect1(5) = varP5(1)
                Rect1(6) = varP7(0): Rect1(7) = varP7(1)
                Set LwpLine1 = ThisDrawing.ModelSpace.AddLightWeightPolyline(Rect1)
                LwpLine1.Closed = True
                LwpLine1.Layer = "SB"
                LwpLine1.Update
                Set objText = ThisDrawing.ModelSpace.AddText(txtN + CStr(intNum) + "(" + txtW + ")", varP12, 40)
                objText.Alignment = acAlignmentBottomCenter
                objText.ScaleFactor = 0.7
                objText.Layer = "BEAMT"
                objText.StyleName = "C40"
                objText.TextAlignmentPoint = varP12
                objText.Rotate varP12, Ang1
                Tra1(0) = varP8(0): Tra1(1) = varP8(1)
                Tra1(2) = varP6(0): Tra1(3) = varP6(1)
                Tra1(4) = varP9(0): Tra1(5) = varP9(1)
                Set LwpLine1 = ThisDrawing.ModelSpace.AddLightWeightPolyline(Tra1)
                LwpLine1.Closed = True
                LwpLine1.Color = acYellow
                LwpLine1.Layer = "SB"
                LwpLine1.Update
                ' Create the associative Hatch object
                Set objHat = ThisDrawing.ModelSpace.AddHatch(PatternType, patternName, bAssociativity)

                ' Create the outer boundary for the hatch
                Set outerLoop(0) = LwpLine1
                objHat.AppendOuterLoop (outerLoop)
                objHat.Layer = "SB"
                objHat.Color = acYellow
                objHat.Update
                Tra1(0) = varP4(0): Tra1(1) = varP4(1)
                Tra1(2) = varP10(0): Tra1(3) = varP10(1)
                Tra1(4) = varP11(0): Tra1(5) = varP11(1)
                Set LwpLine1 = ThisDrawing.ModelSpace.AddLightWeightPolyline(Tra1)
                LwpLine1.Closed = True
                LwpLine1.Color = acYellow
                LwpLine1.Layer = "SB"
                LwpLine1.Update
                ' Create the associative Hatch object
                Set objHat = ThisDrawing.ModelSpace.AddHatch(PatternType, patternName, bAssociativity)

                ' Create the outer boundary for the hatch
                Set outerLoop(0) = LwpLine1
                objHat.AppendOuterLoop (outerLoop)
                objHat.Layer = "SB"
                objHat.Color = acYellow
                objHat.Update
            ElseIf chkMiddle.Value = True Then
                With ThisDrawing.Utility
                    varP0 = .GetPoint(, "P1")
                    varP1 = .GetPoint(varP0, "P2")
                    Dist1 = GetDistance(varP0, varP1)
                    Ang1 = .AngleFromXAxis(varP0, varP1)
                    varP2 = .PolarPoint(varP0, Ang1, 20)
                    varP3 = .PolarPoint(varP1, Ang1, -20)
                    varP4 = .PolarPoint(varP3, PI / 2 + Ang1, dblW / 2)
                    varP5 = .PolarPoint(varP3, PI / 2 + Ang1, dblW)
                    varP6 = .PolarPoint(varP2, PI / 2 + Ang1, dblW / 2)
                    varP7 = .PolarPoint(varP2, PI / 2 + Ang1, dblW)
                    varP8 = .PolarPoint(varP0, PI / 2 + Ang1, (dblW - 20) / 2)
                    varP9 = .PolarPoint(varP0, PI / 2 + Ang1, (dblW - 20) / 2 + 20)
                    varP10 = .PolarPoint(varP1, PI / 2 + Ang1, (dblW - 20) / 2)
                    varP11 = .PolarPoint(varP1, PI / 2 + Ang1, (dblW - 20) / 2 + 20)
                    varP12 = .PolarPoint(varP7, Ang1, Dist1 / 2 - 20)
                    varP12 = .PolarPoint(varP12, Ang1 + PI / 2, 5)
                End With
                Rect1(0) = varP2(0): Rect1(1) = varP2(1)
                Rect1(2) = varP3(0): Rect1(3) = varP3(1)
                Rect1(4) = varP5(0): Rect1(5) = varP5(1)
                Rect1(6) = varP7(0): Rect1(7) = varP7(1)
                Set LwpLine1 = ThisDrawing.ModelSpace.AddLightWeightPolyline(Rect1)
                LwpLine1.Closed = True
                LwpLine1.Layer = "SB"
                LwpLine1.Move varP6, varP2
                LwpLine1.Update
                Set objText = ThisDrawing.ModelSpace.AddText(txtN + CStr(intNum) + "(" + txtW + ")", varP12, 40)
                objText.Alignment = acAlignmentBottomCenter
                objText.ScaleFactor = 0.7
                objText.Layer = "BEAMT"
                objText.StyleName = "C40"
                objText.TextAlignmentPoint = varP12
                objText.Rotate varP12, Ang1
                objText.Move varP6, varP2
                objText.Update
                Tra1(0) = varP8(0): Tra1(1) = varP8(1)
                Tra1(2) = varP6(0): Tra1(3) = varP6(1)
                Tra1(4) = varP9(0): Tra1(5) = varP9(1)
                Set LwpLine1 = ThisDrawing.ModelSpace.AddLightWeightPolyline(Tra1)
                LwpLine1.Closed = True
                LwpLine1.Color = acYellow
                LwpLine1.Layer = "SB"
                LwpLine1.Move varP6, varP2
                LwpLine1.Update
                ' Create the associative Hatch object
                Set objHat = ThisDrawing.ModelSpace.AddHatch(PatternType, patternName, bAssociativity)

                ' Create the outer boundary for the hatch
                Set outerLoop(0) = LwpLine1
                objHat.AppendOuterLoop (outerLoop)
                objHat.Layer = "SB"
                objHat.Color = acYellow
                objHat.Update
                Tra1(0) = varP4(0): Tra1(1) = varP4(1)
                Tra1(2) = varP10(0): Tra1(3) = varP10(1)
                Tra1(4) = varP11(0): Tra1(5) = varP11(1)
                Set LwpLine1 = ThisDrawing.ModelSpace.AddLightWeightPolyline(Tra1)
                LwpLine1.Closed = True
                LwpLine1.Color = acYellow
                LwpLine1.Layer = "SB"
                LwpLine1.Move varP6, varP2
                LwpLine1.Update
                ' Create the associative Hatch object
                Set objHat = ThisDrawing.ModelSpace.AddHatch(PatternType, patternName, bAssociativity)

                ' Create the outer boundary for the hatch
                Set outerLoop(0) = LwpLine1
                objHat.AppendOuterLoop (outerLoop)
                objHat.Layer = "SB"
                objHat.Color = acYellow
                objHat.Update
            ElseIf chkDown.Value = True Then
                With ThisDrawing.Utility
                    varP0 = .GetPoint(, "P1")
                    varP1 = .GetPoint(varP0, "P2")
                    Dist1 = GetDistance(varP0, varP1)
                    Ang1 = .AngleFromXAxis(varP0, varP1)
                    varP2 = .PolarPoint(varP0, Ang1, 20)
                    varP3 = .PolarPoint(varP1, Ang1, -20)
                    varP4 = .PolarPoint(varP3, PI / 2 + Ang1, dblW / 2)
                    varP5 = .PolarPoint(varP3, PI / 2 + Ang1, dblW)
                    varP6 = .PolarPoint(varP2, PI / 2 + Ang1, dblW / 2)
                    varP7 = .PolarPoint(varP2, PI / 2 + Ang1, dblW)
                    varP8 = .PolarPoint(varP0, PI / 2 + Ang1, (dblW - 20) / 2)
                    varP9 = .PolarPoint(varP0, PI / 2 + Ang1, (dblW - 20) / 2 + 20)
                    varP10 = .PolarPoint(varP1, PI / 2 + Ang1, (dblW - 20) / 2)
                    varP11 = .PolarPoint(varP1, PI / 2 + Ang1, (dblW - 20) / 2 + 20)
                    varP12 = .PolarPoint(varP7, Ang1, Dist1 / 2 - 20)
                    varP12 = .PolarPoint(varP12, Ang1 + PI / 2, 5)
                End With
                Rect1(0) = varP2(0): Rect1(1) = varP2(1)
                Rect1(2) = varP3(0): Rect1(3) = varP3(1)
                Rect1(4) = varP5(0): Rect1(5) = varP5(1)
                Rect1(6) = varP7(0): Rect1(7) = varP7(1)
                Set LwpLine1 = ThisDrawing.ModelSpace.AddLightWeightPolyline(Rect1)
                LwpLine1.Closed = True
                LwpLine1.Layer = "SB"
                LwpLine1.Move varP7, varP2
                LwpLine1.Update
                Set objText = ThisDrawing.ModelSpace.AddText(txtN + CStr(intNum) + "(" + txtW + ")", varP12, 40)
                objText.Alignment = acAlignmentBottomCenter
                objText.ScaleFactor = 0.7
                objText.Layer = "BEAMT"
                objText.StyleName = "C40"
                objText.TextAlignmentPoint = varP12
                objText.Rotate varP12, Ang1
                objText.Move varP7, varP2
                objText.Update
                Tra1(0) = varP8(0): Tra1(1) = varP8(1)
                Tra1(2) = varP6(0): Tra1(3) = varP6(1)
                Tra1(4) = varP9(0): Tra1(5) = varP9(1)
                Set LwpLine1 = ThisDrawing.ModelSpace.AddLightWeightPolyline(Tra1)
                LwpLine1.Closed = True
                LwpLine1.Color = acYellow
                LwpLine1.Layer = "SB"
                LwpLine1.Move varP7, varP2
                LwpLine1.Update
                ' Create the associative Hatch object
                Set objHat = ThisDrawing.ModelSpace.AddHatch(PatternType, patternName, bAssociativity)

                ' Create the outer boundary for the hatch
                Set outerLoop(0) = LwpLine1
                objHat.AppendOuterLoop (outerLoop)
                objHat.Layer = "SB"
                objHat.Color = acYellow
                objHat.Update
                Tra1(0) = varP4(0): Tra1(1) = varP4(1)
                Tra1(2) = varP10(0): Tra1(3) = varP10(1)
                Tra1(4) = varP11(0): Tra1(5) = varP11(1)
                Set LwpLine1 = ThisDrawing.ModelSpace.AddLightWeightPolyline(Tra1)
                LwpLine1.Closed = True
                LwpLine1.Color = acYellow
                LwpLine1.Layer = "SB"
                LwpLine1.Move varP7, varP2
                LwpLine1.Update
                ' Create the associative Hatch object
                Set objHat = ThisDrawing.ModelSpace.AddHatch(PatternType, patternName, bAssociativity)

                ' Create the outer boundary for the hatch
                Set outerLoop(0) = LwpLine1
                objHat.AppendOuterLoop (outerLoop)
                objHat.Layer = "SB"
                objHat.Color = acYellow
                objHat.Update
            End If
    Loop
    End If
Z:
    Me.txtNum = CStr(intNum)
    Me.show
End Sub

Attribute VB_Name = "SSBeamsJr"
Attribute VB_Base = "0{B34D1BFC-A919-4459-B08B-D2F43CE0C773}{D414D2F1-08B8-488E-B022-81BC6DB1B71B}"
Attribute VB_GlobalNameSpace = False
Attribute VB_Creatable = False
Attribute VB_PredeclaredId = True
Attribute VB_Exposed = False
Attribute VB_TemplateDerived = False
Attribute VB_Customizable = False
Private Sub chkDown_Click()
    If Me.chkDown.Value = True Then
        Me.chkUp.Value = False
        Me.chkMiddle.Value = False
    End If
End Sub

Private Sub chkJrdown_Click()
    If Me.chkJrdown.Value = True Then
        Me.chkJrup.Value = False
    End If
End Sub

Private Sub chkJrup_Click()
    If Me.chkJrup.Value = True Then
        Me.chkJrdown.Value = False
    End If
End Sub

Private Sub chkMiddle_Click()
    If Me.chkMiddle.Value = True Then
        Me.chkUp.Value = False
        Me.chkDown.Value = False
    End If
End Sub

Private Sub chkUp_Click()
    If Me.chkUp.Value = True Then
        Me.chkMiddle.Value = False
        Me.chkDown.Value = False
    End If
End Sub

Private Sub chkAuto_Click()
    If Me.chkAuto.Value = True Then
        Me.chkUp.Visible = False
        Me.chkMiddle.Visible = False
        Me.chkDown.Visible = False
        Me.Label5.Visible = False
        Me.Label7.Visible = False
        Me.Label8.Visible = False
        Me.Label9.Visible = False
        Me.Label4.Visible = True
        Me.txtHowMany.Visible = True
    Else
        Me.chkUp.Visible = True
        Me.chkMiddle.Visible = True
        Me.chkDown.Visible = True
        Me.Label5.Visible = True
        Me.Label7.Visible = True
        Me.Label8.Visible = True
        Me.Label9.Visible = True
        Me.Label4.Visible = False
        Me.txtHowMany.Visible = False
    End If
End Sub

Private Sub cmdCancel_Click()
    Me.Hide
    BasicForm.show
End Sub


Private Sub cmdDraw_Click()
    Dim objAcadEntity As AcadEntity
    Dim LwpLine1 As AcadLWPolyline
    Dim LwpLine2 As AcadLWPolyline
    Dim LwpLine3 As AcadLWPolyline
    Dim testC As AcadCircle
    Dim varP0(0 To 3) As Double
    Dim dblW, Dist1, Dist2, Dist3, Dist4, Ang1, Ang2, Dist5, Dist6, Dist7, Dist8, Dist9 As Double
    Dim intHowMany As Integer
    Dim varP1(0 To 2) As Double
    Dim varP2(0 To 2) As Double
    Dim varPa(0 To 2) As Double
    Dim varPb(0 To 2) As Double
    Dim varP3, varP4, varP5, varP6, varP7, varP8, varP9, varP10, varP9a As Variant
    Dim Rect1(0 To 7) As Double
    Dim i As Integer
    Dim copyL3 As AcadLWPolyline
    Dim strN As String
    Dim intNum As Integer
    Dim objText As AcadText
    Dim copyText As AcadText
    
Me.Hide
Call CreateLayer("SJ", 31, "CONTINUOUS")
Call CreateLayer("SJT", 71, "CONTINUOUS")
dblW = Val(Me.txtW.Value)
intNum = Val(Me.txtNum)
strN = Me.txtN
intHowMany = Val(Me.txtHowMany)
On Error GoTo Z
    If Me.chkAuto.Value = True Then
        Call ThisDrawing.Utility.GetEntity(objAcadEntity, varPickPoint, "請選擇樑")
        If TypeOf objAcadEntity Is AcadLWPolyline Then
            Set LwpLine1 = objAcadEntity
        Else
            GoTo Z
        End If
        Call ThisDrawing.Utility.GetEntity(objAcadEntity, varPickPoint, "請選擇樑")
        If TypeOf objAcadEntity Is AcadLWPolyline Then
            Set LwpLine2 = objAcadEntity
        Else
            GoTo Z
        End If
        varP0(0) = (LwpLine1.Coordinates(0) + LwpLine1.Coordinates(2) + LwpLine1.Coordinates(4) + LwpLine1.Coordinates(6)) / 4
        varP0(1) = (LwpLine1.Coordinates(1) + LwpLine1.Coordinates(3) + LwpLine1.Coordinates(5) + LwpLine1.Coordinates(7)) / 4
        varP0(2) = (LwpLine2.Coordinates(0) + LwpLine2.Coordinates(2) + LwpLine2.Coordinates(4) + LwpLine2.Coordinates(6)) / 4
        varP0(3) = (LwpLine2.Coordinates(1) + LwpLine2.Coordinates(3) + LwpLine2.Coordinates(5) + LwpLine2.Coordinates(7)) / 4
        Dist1 = ((LwpLine1.Coordinates(0) - LwpLine1.Coordinates(2)) ^ 2 + (LwpLine1.Coordinates(1) - LwpLine1.Coordinates(3)) ^ 2) ^ 0.5
        Dist2 = ((LwpLine1.Coordinates(4) - LwpLine1.Coordinates(2)) ^ 2 + (LwpLine1.Coordinates(5) - LwpLine1.Coordinates(3)) ^ 2) ^ 0.5
        Dist3 = ((LwpLine2.Coordinates(0) - LwpLine2.Coordinates(2)) ^ 2 + (LwpLine2.Coordinates(1) - LwpLine2.Coordinates(3)) ^ 2) ^ 0.5
        Dist4 = ((LwpLine2.Coordinates(4) - LwpLine2.Coordinates(2)) ^ 2 + (LwpLine2.Coordinates(5) - LwpLine2.Coordinates(3)) ^ 2) ^ 0.5
        If Dist1 < Dist2 Then
        ElseIf Dist1 > Dist2 Then
            Dist1 = Dist2
        Else
        End If
        If Dist3 < Dist4 Then
        ElseIf Dist3 > Dist4 Then
            Dist3 = Dist4
        Else
        End If
        varP1(0) = varP0(0)
        varP1(1) = varP0(1)
        varP1(2) = 0
        varP2(0) = varP0(2)
        varP2(1) = varP0(3)
        varP2(2) = 0
        varPa(0) = LwpLine1.Coordinates(2)
        varPa(1) = LwpLine1.Coordinates(3)
        varPa(2) = 0
        varPb(0) = LwpLine1.Coordinates(4)
        varPb(1) = LwpLine1.Coordinates(5)
        varPb(2) = 0
'        Set testC = ThisDrawing.ModelSpace.AddCircle(varP1, 10)
        Ang1 = ThisDrawing.Utility.AngleFromXAxis(varP1, varP2)
        Dist8 = GetDistance(varP1, varP2)
        If Ang1 <> Ang2 Then
            If Me.chkJrup.Value = True Then
            Ang2 = ThisDrawing.Utility.AngleFromXAxis(varPa, varPb)
            Ang1 = Ang2
            ElseIf Me.chkJrdown.Value = True Then
            Ang2 = ThisDrawing.Utility.AngleFromXAxis(varPb, varPa)
            Ang1 = Ang2
            End If
            varP3 = ThisDrawing.Utility.PolarPoint(varP1, Ang1, Dist1 / 2 + 10)
            varP4 = ThisDrawing.Utility.PolarPoint(varP1, Ang1, Dist8 - Dist2 / 2 - 10)
            varP5 = ThisDrawing.Utility.PolarPoint(varP3, Ang1 + PI / 2, dblW / 2)
            varP6 = ThisDrawing.Utility.PolarPoint(varP3, Ang1 - PI / 2, dblW / 2)
            varP7 = ThisDrawing.Utility.PolarPoint(varP4, Ang1 + PI / 2, dblW / 2)
            varP8 = ThisDrawing.Utility.PolarPoint(varP4, Ang1 - PI / 2, dblW / 2)
        Else
            varP3 = ThisDrawing.Utility.PolarPoint(varP1, Ang1, Dist1 / 2 + 10)
            varP4 = ThisDrawing.Utility.PolarPoint(varP2, Ang1, -Dist2 / 2 - 10)
            varP5 = ThisDrawing.Utility.PolarPoint(varP3, Ang1 + PI / 2, dblW / 2)
            varP6 = ThisDrawing.Utility.PolarPoint(varP3, Ang1 - PI / 2, dblW / 2)
            varP7 = ThisDrawing.Utility.PolarPoint(varP4, Ang1 + PI / 2, dblW / 2)
            varP8 = ThisDrawing.Utility.PolarPoint(varP4, Ang1 - PI / 2, dblW / 2)
        End If
        Dist7 = GetDistance(varP6, varP8)
        Rect1(0) = varP5(0): Rect1(1) = varP5(1)
        Rect1(2) = varP6(0): Rect1(3) = varP6(1)
        Rect1(4) = varP8(0): Rect1(5) = varP8(1)
        Rect1(6) = varP7(0): Rect1(7) = varP7(1)
        varP9 = ThisDrawing.Utility.PolarPoint(varP5, Ang1, Dist7 / 2)
        varP9a = ThisDrawing.Utility.PolarPoint(varP9, Ang1 + PI / 2, 5)
'        Set testC = ThisDrawing.ModelSpace.AddCircle(varP9, 10)
        Set LwpLine3 = ThisDrawing.ModelSpace.AddLightWeightPolyline(Rect1)
        LwpLine3.Closed = True
        LwpLine3.Layer = "SJ"
        LwpLine3.Update
        Set objText = ThisDrawing.ModelSpace.AddText(strN + CStr(intNum) + "(" + txtW + ")", varP9a, 40)
        objText.StyleName = "C40"
        objText.ScaleFactor = 0.7
        objText.Alignment = acAlignmentBottomCenter
        objText.TextAlignmentPoint = varP9a
        objText.Rotate varP9a, Ang1
        objText.Layer = "SJT"
        objText.Update
        If intHowMany Mod 2 = 0 Then
            Dist1 = ((LwpLine1.Coordinates(0) - LwpLine1.Coordinates(2)) ^ 2 + (LwpLine1.Coordinates(1) - LwpLine1.Coordinates(3)) ^ 2) ^ 0.5
            Dist2 = ((LwpLine1.Coordinates(4) - LwpLine1.Coordinates(2)) ^ 2 + (LwpLine1.Coordinates(5) - LwpLine1.Coordinates(3)) ^ 2) ^ 0.5
            Dist3 = ((LwpLine2.Coordinates(0) - LwpLine2.Coordinates(2)) ^ 2 + (LwpLine2.Coordinates(1) - LwpLine2.Coordinates(3)) ^ 2) ^ 0.5
            Dist4 = ((LwpLine2.Coordinates(4) - LwpLine2.Coordinates(2)) ^ 2 + (LwpLine2.Coordinates(5) - LwpLine2.Coordinates(3)) ^ 2) ^ 0.5
            If Dist1 > Dist2 Then
            ElseIf Dist1 < Dist2 Then
                Dist1 = Dist2
            Else
            End If
            If Dist3 > Dist4 Then
            ElseIf Dist3 < Dist4 Then
                Dist3 = Dist4
            Else
            End If
            Dist5 = (Dist1 - intHowMany * dblW) / (intHowMany + 1)
'            Dist6 = Dist3 / (intHowMany + 1)
            varP9 = ThisDrawing.Utility.PolarPoint(varP1, Ang1 + PI / 2, (Dist5 + dblW) / 2)
            varP10 = ThisDrawing.Utility.PolarPoint(varP1, Ang1 + PI / 2, (Dist5 + dblW) / -2)
            For i = 2 To intHowMany Step 2
                Set copyL3 = LwpLine3.Copy()
                Set copyText = objText.Copy()
                copyL3.Move varP1, varP9
                copyText.Move varP1, varP9
                copyL3.Update
                copyText.Update
                Set copyL3 = LwpLine3.Copy()
                Set copyText = objText.Copy()
                copyL3.Move varP1, varP10
                copyText.Move varP1, varP10
                copyL3.Update
                copyText.Update
                varP9 = ThisDrawing.Utility.PolarPoint(varP9, Ang1 + PI / 2, Dist5 + dblW)
                varP10 = ThisDrawing.Utility.PolarPoint(varP10, Ang1 + PI / 2, -Dist5 - dblW)
            Next
            LwpLine3.Delete
            objText.Delete
            ThisDrawing.Application.Update
        Else
            Dist1 = ((LwpLine1.Coordinates(0) - LwpLine1.Coordinates(2)) ^ 2 + (LwpLine1.Coordinates(1) - LwpLine1.Coordinates(3)) ^ 2) ^ 0.5
            Dist2 = ((LwpLine1.Coordinates(4) - LwpLine1.Coordinates(2)) ^ 2 + (LwpLine1.Coordinates(5) - LwpLine1.Coordinates(3)) ^ 2) ^ 0.5
            Dist3 = ((LwpLine2.Coordinates(0) - LwpLine2.Coordinates(2)) ^ 2 + (LwpLine2.Coordinates(1) - LwpLine2.Coordinates(3)) ^ 2) ^ 0.5
            Dist4 = ((LwpLine2.Coordinates(4) - LwpLine2.Coordinates(2)) ^ 2 + (LwpLine2.Coordinates(5) - LwpLine2.Coordinates(3)) ^ 2) ^ 0.5
            If Dist1 > Dist2 Then
            ElseIf Dist1 < Dist2 Then
                Dist1 = Dist2
            Else
            End If
            If Dist3 > Dist4 Then
            ElseIf Dist3 < Dist4 Then
                Dist3 = Dist4
            Else
            End If
            Dist5 = (Dist1 - intHowMany * dblW) / (intHowMany + 1)
            varP9 = ThisDrawing.Utility.PolarPoint(varP1, Ang1 + PI / 2, Dist5 + dblW)
            varP10 = ThisDrawing.Utility.PolarPoint(varP1, Ang1 + PI / 2, -Dist5 - dblW)
            For i = 1 To intHowMany - 2 Step 2
                Set copyL3 = LwpLine3.Copy()
                Set copyText = objText.Copy()
                copyL3.Move varP1, varP9
                copyText.Move varP1, varP9
                copyL3.Update
                copyText.Update
                Set copyL3 = LwpLine3.Copy()
                Set copyText = objText.Copy()
                copyL3.Move varP1, varP10
                copyText.Move varP1, varP10
                copyL3.Update
                copyText.Update
                varP9 = ThisDrawing.Utility.PolarPoint(varP9, Ang1 + PI / 2, Dist5 + dblW)
                varP10 = ThisDrawing.Utility.PolarPoint(varP10, Ang1 + PI / 2, -Dist5 - dblW)
            Next
        End If
    Else
    If Me.chkUp.Value = True Then
        With ThisDrawing.Utility
            varP3 = .GetPoint(, "P1")
            varP4 = .GetPoint(varP3, "P2")
            Dist1 = GetDistance(varP3, varP4)
            Ang1 = .AngleFromXAxis(varP3, varP4)
            varP5 = .PolarPoint(varP3, Ang1, 10)
            varP6 = .PolarPoint(varP4, Ang1, -10)
            varP7 = .PolarPoint(varP6, PI / 2 + Ang1, dblW)
            varP8 = .PolarPoint(varP5, PI / 2 + Ang1, dblW)
            varP9 = .PolarPoint(varP8, Ang1, Dist1 / 2 - 10)
            varP9a = .PolarPoint(varP9, Ang1 + PI / 2, 5)
        End With
        Rect1(0) = varP5(0): Rect1(1) = varP5(1)
        Rect1(2) = varP6(0): Rect1(3) = varP6(1)
        Rect1(4) = varP7(0): Rect1(5) = varP7(1)
        Rect1(6) = varP8(0): Rect1(7) = varP8(1)
        Set objText = ThisDrawing.ModelSpace.AddText(strN + CStr(intNum) + "(" + txtW + ")", varP9a, 40)
        objText.StyleName = "C40"
        objText.ScaleFactor = 0.7
        objText.Alignment = acAlignmentBottomCenter
        objText.TextAlignmentPoint = varP9a
        objText.Rotate varP9a, Ang1
        objText.Layer = "SJT"
        objText.Update
        Set LwpLine3 = ThisDrawing.ModelSpace.AddLightWeightPolyline(Rect1)
        LwpLine3.Closed = True
        LwpLine3.Layer = "SJ"
        LwpLine3.Update
    ElseIf Me.chkMiddle.Value = True Then
        With ThisDrawing.Utility
            varP3 = .GetPoint(, "P1")
            varP4 = .GetPoint(varP3, "P2")
            Dist1 = GetDistance(varP3, varP4)
            Ang1 = .AngleFromXAxis(varP3, varP4)
            varP5 = .PolarPoint(varP3, Ang1, 10)
            varP6 = .PolarPoint(varP4, Ang1, -10)
            varP7 = .PolarPoint(varP6, PI / 2 + Ang1, dblW)
            varP8 = .PolarPoint(varP5, PI / 2 + Ang1, dblW)
            varP9 = .PolarPoint(varP5, PI / 2 + Ang1, dblW / 2)
            varP10 = .PolarPoint(varP8, Ang1, Dist1 / 2 - 10)
            varP9a = .PolarPoint(varP10, Ang1 + PI / 2, 5)
        End With
        Rect1(0) = varP5(0): Rect1(1) = varP5(1)
        Rect1(2) = varP6(0): Rect1(3) = varP6(1)
        Rect1(4) = varP7(0): Rect1(5) = varP7(1)
        Rect1(6) = varP8(0): Rect1(7) = varP8(1)
        Set objText = ThisDrawing.ModelSpace.AddText(strN + CStr(intNum) + "(" + txtW + ")", varP9a, 40)
        objText.StyleName = "C40"
        objText.ScaleFactor = 0.7
        objText.Alignment = acAlignmentBottomCenter
        objText.TextAlignmentPoint = varP9a
        objText.Rotate varP9a, Ang1
        objText.Move varP9, varP5
        objText.Layer = "SJT"
        objText.Update
        Set LwpLine3 = ThisDrawing.ModelSpace.AddLightWeightPolyline(Rect1)
        LwpLine3.Closed = True
        LwpLine3.Layer = "SJ"
        LwpLine3.Move varP9, varP5
        LwpLine3.Update
    ElseIf Me.chkDown.Value = True Then
        With ThisDrawing.Utility
            varP3 = .GetPoint(, "P1")
            varP4 = .GetPoint(varP3, "P2")
            Dist1 = GetDistance(varP3, varP4)
            Ang1 = .AngleFromXAxis(varP3, varP4)
            varP5 = .PolarPoint(varP3, Ang1, 10)
            varP6 = .PolarPoint(varP4, Ang1, -10)
            varP7 = .PolarPoint(varP6, PI / 2 + Ang1, dblW)
            varP8 = .PolarPoint(varP5, PI / 2 + Ang1, dblW)
            varP9 = .PolarPoint(varP8, Ang1, Dist1 / 2 - 10)
            varP9a = .PolarPoint(varP9, Ang1 + PI / 2, 5)
        End With
        Rect1(0) = varP5(0): Rect1(1) = varP5(1)
        Rect1(2) = varP6(0): Rect1(3) = varP6(1)
        Rect1(4) = varP7(0): Rect1(5) = varP7(1)
        Rect1(6) = varP8(0): Rect1(7) = varP8(1)
        Set objText = ThisDrawing.ModelSpace.AddText(strN + CStr(intNum) + "(" + txtW + ")", varP9a, 40)
        objText.StyleName = "C40"
        objText.ScaleFactor = 0.7
        objText.Alignment = acAlignmentBottomCenter
        objText.TextAlignmentPoint = varP9a
        objText.Rotate varP9a, Ang1
        objText.Move varP8, varP5
        objText.Layer = "SJT"
        objText.Update
        Set LwpLine3 = ThisDrawing.ModelSpace.AddLightWeightPolyline(Rect1)
        LwpLine3.Closed = True
        LwpLine3.Layer = "SJ"
        LwpLine3.Move varP8, varP5
        LwpLine3.Update
    End If
End If
Z:
Me.show
End Sub

Attribute VB_Name = "SSPanel"
Attribute VB_Base = "0{01B1EE94-EAFE-4730-83D6-47485E70C31C}{6BDB2D92-1AB6-4432-B3F1-7C6C6F568D53}"
Attribute VB_GlobalNameSpace = False
Attribute VB_Creatable = False
Attribute VB_PredeclaredId = True
Attribute VB_Exposed = False
Attribute VB_TemplateDerived = False
Attribute VB_Customizable = False
Private Sub cmdCancel_Click()
    Me.Hide
    BasicForm.show
End Sub

Private Sub cmdDraw_Click()
    Dim strN As String
    Dim strNum As String
    Dim objLine As AcadLWPolyline
    Dim varP0, varP1, varP2, varP3, varP4, varP5, varP6, varP7 As Variant
    Dim Ang1, Dist1 As Double
    Dim Pline(0 To 17) As Double
    Dim objText As AcadText
    Dim pointObj As AcadPoint
    
    Me.Hide
    strN = Me.txtN
    strNum = Me.txtNum
    Call CreateLayer("SLABT", 7, "CONTINUOUS")
    Do While Err.Number = 0
    On Error GoTo Z
    varP0 = ThisDrawing.Utility.GetPoint(, "插入點")
    If Me.chkVertical.Value = True Then
        Ang1 = PI / 2
    Else
        Ang1 = 0
    End If
    With ThisDrawing.Utility
        varP1 = .PolarPoint(varP0, PI + Ang1, 40)
        varP2 = .PolarPoint(varP1, PI / 12 + Ang1, 16)
        varP3 = .PolarPoint(varP1, PI / -12 + Ang1, 16)
        varP4 = .PolarPoint(varP0, Ang1, 40)
        varP5 = .PolarPoint(varP4, PI * 165 / 180 + Ang1, 16)
        varP6 = .PolarPoint(varP4, PI * 165 / -180 + Ang1, 16)
        varP7 = .PolarPoint(varP0, PI / 2 + Ang1, 4)
    End With
    Pline(0) = varP0(0):    Pline(1) = varP0(1)
    Pline(2) = varP1(0):    Pline(3) = varP1(1)
    Pline(4) = varP2(0):    Pline(5) = varP2(1)
    Pline(6) = varP3(0):    Pline(7) = varP3(1)
    Pline(8) = varP1(0):    Pline(9) = varP1(1)
    Pline(10) = varP4(0):    Pline(11) = varP4(1)
    Pline(12) = varP5(0):    Pline(13) = varP5(1)
    Pline(14) = varP6(0):    Pline(15) = varP6(1)
    Pline(16) = varP4(0):    Pline(17) = varP4(1)
    Set objLine = ThisDrawing.ModelSpace.AddLightWeightPolyline(Pline)
    objLine.Layer = "SLABT"
    objLine.Color = acWhite
    objLine.Update
    Set objText = ThisDrawing.ModelSpace.AddText(strN + strNum, varP7, 40)
    objText.Alignment = acAlignmentBottomCenter
    objText.ScaleFactor = 0.7
    objText.TextAlignmentPoint = varP7
    objText.Rotate varP7, Ang1
    objText.Layer = "SLABT"
    objText.StyleName = "C40"
    objText.Color = acWhite
    objText.Update
    Loop
Z:
    Me.show
End Sub

Attribute VB_Name = "SSPillar"
Attribute VB_Base = "0{3AF9A4E0-4559-4248-90F6-CF3CCDEAAAD8}{AD7792D4-D611-4809-BF05-8E691162F930}"
Attribute VB_GlobalNameSpace = False
Attribute VB_Creatable = False
Attribute VB_PredeclaredId = True
Attribute VB_Exposed = False
Attribute VB_TemplateDerived = False
Attribute VB_Customizable = False
Private Sub cmdCancel_Click()
    Me.Hide
    BasicForm.show
End Sub



Private Sub cmdDrawing_Click()
    Dim strID, strN, strRCID, strRCN As String
    Dim intNum, intRCNum As Integer
    Dim varP0, varP1, varP2, varP3, varP4, varP5, varP6, varP7, varP8, varP9, varP10, varP11, varP12, varP13, varP14, varP15, varP16, varP17 As Variant
    Dim Dist1, Dist2, Dist3, Dist4, Dist5, Ang1, Ang2 As Double
    Dim v7a, v8a, v9a, v10a As Variant
    Dim adblCoordinate(0 To 11) As Double
    Dim objAddLightWeightPolyline As AcadLWPolyline
    Dim objText1 As AcadText
    Dim objText2 As AcadText
    Dim arrayCor(0 To 7) As Double
    
    Me.Hide
    Call CreateLayer("SC1", 2, "CONTINUOUS")
    Call CreateLayer("C1", 2, "CONTINUOUS")
    Call CreateLayer("COLT", 1, "CONTINUOUS")
    Call CreateLayer("COLS", 1, "CONTINUOUS")
    intNum = Me.txtNum
    intRCNum = Me.txtRCNum
    strID = Me.txtID
    strN = Me.txtN
    strRCID = Me.txtRCID
    strRCN = Me.txtRCN
    If Me.chkRo.Value = True Then
        GoTo X
    End If
If Me.chkContinue = False Then
    Do While Err.Number = 0
    On Error GoTo Z
    With ThisDrawing.Utility
        varP0 = .GetPoint(, "P1")
        varP1 = .GetCorner(varP0, "P2")
        Dist1 = GetDistance(varP0, varP1)
        Ang1 = .AngleFromXAxis(varP0, varP1)
        Dist2 = Dist1 * Cos(Ang1)
        Dist3 = Dist1 * Sin(Ang1)
        varP2 = .PolarPoint(varP0, 0, Dist2)
        varP3 = .PolarPoint(varP0, 0, Dist2 / 2)
        varP4 = .PolarPoint(varP1, PI, Dist2)
        varP5 = .PolarPoint(varP1, PI, Dist2 / 2)
        adblCoordinate(0) = varP0(0):        adblCoordinate(1) = varP0(1)
        adblCoordinate(2) = varP2(0):        adblCoordinate(3) = varP2(1)
        adblCoordinate(4) = varP3(0):        adblCoordinate(5) = varP3(1)
        adblCoordinate(6) = varP5(0):        adblCoordinate(7) = varP5(1)
        adblCoordinate(8) = varP1(0):        adblCoordinate(9) = varP1(1)
        adblCoordinate(10) = varP4(0):        adblCoordinate(11) = varP4(1)
    End With
    Set objAddLightWeightPolyline = ThisDrawing.ModelSpace.AddLightWeightPolyline(adblCoordinate)
    objAddLightWeightPolyline.Closed = False
    objAddLightWeightPolyline.Layer = "SC1"
    objAddLightWeightPolyline.Update
    If Dist2 Mod 5# <> 0 Then
        Dist4 = (Dist2 \ 5 + 1) * 5
    Else
        Dist4 = Round(Dist2, 0)
    End If
    If Dist3 Mod 5# <> 0 Then
        Dist5 = (Dist3 \ 5 + 1) * 5
    Else
        Dist5 = Round(Dist3, 0)
    End If
    With ThisDrawing.Utility
        varP6 = .PolarPoint(varP3, PI, Dist4 / 2)
        varP7 = .PolarPoint(varP5, 0, Dist4 / 2)
        varP8 = .PolarPoint(varP6, PI / -2, (Dist5 - Dist3) / 2)
        varP9 = .PolarPoint(varP7, PI / 2, (Dist5 - Dist3) / 2)
        varP10 = .PolarPoint(varP8, PI / -2, 60)
        varP11 = .PolarPoint(varP10, PI, 40)
        Set objAddLightWeightPolyline = DrawRectangle(varP8, varP9)
        objAddLightWeightPolyline.Closed = True
        objAddLightWeightPolyline.Layer = "C1"
        objAddLightWeightPolyline.Update
    End With
    If Me.chkRC = False Then
        Set objText1 = ThisDrawing.ModelSpace.AddText(strID + CStr(intNum) + strN, varP10, 40)
        objText1.Layer = "COLT"
        objText1.ScaleFactor = 0.7
        objText1.StyleName = "C40"
        objText1.Alignment = acAlignmentBottomRight
        objText1.TextAlignmentPoint = varP10
        objText1.Update
        Set objText1 = ThisDrawing.ModelSpace.AddText("(" + CStr(Dist4) + "x" + CStr(Dist5) + ")", varP10, 40)
        objText1.Layer = "COLS"
        objText1.ScaleFactor = 0.7
        objText1.StyleName = "C40"
        objText1.Alignment = acAlignmentBottomLeft
        objText1.TextAlignmentPoint = varP10
        objText1.Update
    Else
        With ThisDrawing.Utility
            varP12 = .PolarPoint(varP8, PI, 15)
            varP13 = .PolarPoint(varP9, 0, 15)
            varP14 = .PolarPoint(varP12, PI / -2, 15)
            varP15 = .PolarPoint(varP13, PI / 2, 15)
            varP10 = .PolarPoint(varP14, PI / -2, 60)
            varP11 = .PolarPoint(varP14, PI / -2, 110)
            v7a = .PolarPoint(varP10, PI, 40)
            v8a = .PolarPoint(varP11, PI, 40)
        End With
            Set objAddLightWeightPolyline = DrawRectangle(varP14, varP15)
            objAddLightWeightPolyline.Closed = True
            objAddLightWeightPolyline.Layer = "C1"
            objAddLightWeightPolyline.Update
            Set objText1 = ThisDrawing.ModelSpace.AddText(strID + CStr(intNum) + strN, varP10, 40)
            objText1.Layer = "COLT"
            objText1.ScaleFactor = 0.7
            objText1.StyleName = "C40"
            objText1.Alignment = acAlignmentBottomRight
            objText1.TextAlignmentPoint = varP10
            objText1.Update
            Set objText1 = ThisDrawing.ModelSpace.AddText("(" + CStr(Dist4) + "x" + CStr(Dist5) + ")", varP10, 40)
            objText1.Layer = "COLS"
            objText1.ScaleFactor = 0.7
            objText1.StyleName = "C40"
            objText1.Alignment = acAlignmentBottomLeft
            objText1.TextAlignmentPoint = varP10
            objText1.Update
            Set objText2 = ThisDrawing.ModelSpace.AddText(strRCID + CStr(intRCNum) + strRCN, varP11, 40)
            objText2.Layer = "COLT"
            objText2.ScaleFactor = 0.7
            objText2.StyleName = "C40"
            objText2.Alignment = acAlignmentBottomRight
            objText2.TextAlignmentPoint = varP11
            objText2.Update
            If intRCNum < 10 Then
                varP16 = ThisDrawing.Utility.PolarPoint(v8a, 0, 30)
            ElseIf intRCNum < 100 Then
                varP16 = ThisDrawing.Utility.PolarPoint(v8a, 0, 40)
            Else
                varP16 = ThisDrawing.Utility.PolarPoint(v8a, 0, 50)
            End If
            Set objText2 = ThisDrawing.ModelSpace.AddText("(" + CStr(Dist4 + 30) + "x" + CStr(Dist5 + 30) + ")", varP11, 40)
            objText2.Layer = "COLS"
            objText2.ScaleFactor = 0.7
            objText2.StyleName = "C40"
            objText2.Alignment = acAlignmentBottomLeft
            objText2.TextAlignmentPoint = varP11
            objText2.Update
            objText2.Update
    End If
    Loop
Else
Do While Err.Number = 0
    On Error GoTo Z
    With ThisDrawing.Utility
        varP0 = .GetPoint(, "P1")
        varP1 = .GetCorner(varP0, "P2")
        Dist1 = GetDistance(varP0, varP1)
        Ang1 = .AngleFromXAxis(varP0, varP1)
        Dist2 = Dist1 * Cos(Ang1)
        Dist3 = Dist1 * Sin(Ang1)
        varP2 = .PolarPoint(varP0, 0, Dist2)
        varP3 = .PolarPoint(varP0, 0, Dist2 / 2)
        varP4 = .PolarPoint(varP1, PI, Dist2)
        varP5 = .PolarPoint(varP1, PI, Dist2 / 2)
        adblCoordinate(0) = varP0(0):        adblCoordinate(1) = varP0(1)
        adblCoordinate(2) = varP2(0):        adblCoordinate(3) = varP2(1)
        adblCoordinate(4) = varP3(0):        adblCoordinate(5) = varP3(1)
        adblCoordinate(6) = varP5(0):        adblCoordinate(7) = varP5(1)
        adblCoordinate(8) = varP1(0):        adblCoordinate(9) = varP1(1)
        adblCoordinate(10) = varP4(0):        adblCoordinate(11) = varP4(1)
    End With
    Set objAddLightWeightPolyline = ThisDrawing.ModelSpace.AddLightWeightPolyline(adblCoordinate)
    objAddLightWeightPolyline.Closed = False
    objAddLightWeightPolyline.Layer = "SC1"
    objAddLightWeightPolyline.Update
    If Dist2 Mod 5# <> 0 Then
        Dist4 = (Dist2 \ 5 + 1) * 5
    Else
        Dist4 = Round(Dist2, 0)
    End If
    If Dist3 Mod 5# <> 0 Then
        Dist5 = (Dist3 \ 5 + 1) * 5
    Else
        Dist5 = Round(Dist3, 0)
    End If
    With ThisDrawing.Utility
        varP6 = .PolarPoint(varP3, PI, Dist4 / 2)
        varP7 = .PolarPoint(varP5, 0, Dist4 / 2)
        varP8 = .PolarPoint(varP6, PI / -2, (Dist5 - Dist3) / 2)
        varP9 = .PolarPoint(varP7, PI / 2, (Dist5 - Dist3) / 2)
        varP10 = .PolarPoint(varP8, PI / -2, 60)
        varP11 = .PolarPoint(varP10, PI, 40)
        Set objAddLightWeightPolyline = DrawRectangle(varP8, varP9)
        objAddLightWeightPolyline.Closed = True
        objAddLightWeightPolyline.Layer = "C1"
        objAddLightWeightPolyline.Update
    End With
    If Me.chkRC = False Then
        Set objText1 = ThisDrawing.ModelSpace.AddText(strID + CStr(intNum) + strN, varP10, 40)
        objText1.Layer = "COLT"
        objText1.ScaleFactor = 0.7
        objText1.StyleName = "C40"
        objText1.Alignment = acAlignmentBottomRight
        objText1.TextAlignmentPoint = varP10
        objText1.Update
        Set objText1 = ThisDrawing.ModelSpace.AddText("(" + CStr(Dist4) + "x" + CStr(Dist5) + ")", varP10, 40)
        objText1.Layer = "COLS"
        objText1.ScaleFactor = 0.7
        objText1.StyleName = "C40"
        objText1.Alignment = acAlignmentBottomLeft
        objText1.TextAlignmentPoint = varP10
        objText1.Update
            intNum = intNum + 1
            txtNum = intNum
            intRCNum = intRCNum + 1
            txtRCNum = intRCNum
    Else
        With ThisDrawing.Utility
            varP12 = .PolarPoint(varP8, PI, 15)
            varP13 = .PolarPoint(varP9, 0, 15)
            varP14 = .PolarPoint(varP12, PI / -2, 15)
            varP15 = .PolarPoint(varP13, PI / 2, 15)
            varP10 = .PolarPoint(varP14, PI / -2, 60)
            varP11 = .PolarPoint(varP14, PI / -2, 110)
            v7a = .PolarPoint(varP10, PI, 40)
            v8a = .PolarPoint(varP11, PI, 40)
        End With
            Set objAddLightWeightPolyline = DrawRectangle(varP14, varP15)
            objAddLightWeightPolyline.Closed = True
            objAddLightWeightPolyline.Layer = "C1"
            objAddLightWeightPolyline.Update
            Set objText1 = ThisDrawing.ModelSpace.AddText(strID + CStr(intNum) + strN, varP10, 40)
            objText1.Layer = "COLT"
            objText1.ScaleFactor = 0.7
            objText1.StyleName = "C40"
            objText1.Alignment = acAlignmentBottomRight
            objText1.TextAlignmentPoint = varP10
            objText1.Update
            Set objText1 = ThisDrawing.ModelSpace.AddText("(" + CStr(Dist4) + "x" + CStr(Dist5) + ")", varP10, 40)
            objText1.Layer = "COLS"
            objText1.ScaleFactor = 0.7
            objText1.StyleName = "C40"
            objText1.Alignment = acAlignmentBottomLeft
            objText1.TextAlignmentPoint = varP10
            objText1.Update
            Set objText2 = ThisDrawing.ModelSpace.AddText(strRCID + CStr(intRCNum) + strRCN, varP11, 40)
            objText2.Layer = "COLT"
            objText2.ScaleFactor = 0.7
            objText2.StyleName = "C40"
            objText2.Alignment = acAlignmentBottomRight
            objText2.TextAlignmentPoint = varP11
            objText2.Update
            If intRCNum < 10 Then
                varP16 = ThisDrawing.Utility.PolarPoint(v8a, 0, 30)
            ElseIf intRCNum < 100 Then
                varP16 = ThisDrawing.Utility.PolarPoint(v8a, 0, 40)
            Else
                varP16 = ThisDrawing.Utility.PolarPoint(v8a, 0, 50)
            End If
            Set objText2 = ThisDrawing.ModelSpace.AddText("(" + CStr(Dist4 + 30) + "x" + CStr(Dist5 + 30) + ")", varP11, 40)
            objText2.Layer = "COLS"
            objText2.ScaleFactor = 0.7
            objText2.StyleName = "C40"
            objText2.Alignment = acAlignmentBottomLeft
            objText2.TextAlignmentPoint = varP11
            objText2.Update
            intNum = intNum + 1
            txtNum = intNum
            intRCNum = intRCNum + 1
            txtRCNum = intRCNum
    End If
Loop
End If
GoTo Z
X:
If Me.chkContinue.Value = True Then
    On Error GoTo Z
    Do While Err.Number = 0
        With ThisDrawing.Utility
            varP0 = .GetPoint(, "P1")
            varP1 = .GetPoint(varP0, "Rotate Angle")
            varP2 = .GetPoint(varP1, "P2")
            Dist1 = GetDistance(varP0, varP1)
            Dist2 = GetDistance(varP1, varP2)
            Ang1 = .AngleFromXAxis(varP0, varP1)
            varP3 = .PolarPoint(varP0, Ang1, Dist1 / 2)
            varP4 = .PolarPoint(varP3, PI / 2 + Ang1, Dist2)
            varP5 = .PolarPoint(varP1, PI / 2 + Ang1, Dist2)
            varP6 = .PolarPoint(varP0, PI / 2 + Ang1, Dist2)
        End With
        adblCoordinate(0) = varP0(0):        adblCoordinate(1) = varP0(1)
        adblCoordinate(2) = varP1(0):        adblCoordinate(3) = varP1(1)
        adblCoordinate(4) = varP3(0):        adblCoordinate(5) = varP3(1)
        adblCoordinate(6) = varP4(0):        adblCoordinate(7) = varP4(1)
        adblCoordinate(8) = varP5(0):        adblCoordinate(9) = varP5(1)
        adblCoordinate(10) = varP6(0):        adblCoordinate(11) = varP6(1)
        Set objAddLightWeightPolyline = ThisDrawing.ModelSpace.AddLightWeightPolyline(adblCoordinate)
        objAddLightWeightPolyline.Closed = False
        objAddLightWeightPolyline.Layer = "SC1"
        objAddLightWeightPolyline.Update
        If Dist1 Mod 5# <> 0 Then
            Dist4 = (Dist1 \ 5 + 1) * 5
        Else
            Dist4 = Round(Dist1, 0)
        End If
        If Dist2 Mod 5# <> 0 Then
            Dist5 = (Dist2 \ 5 + 1) * 5
        Else
            Dist5 = Round(Dist2, 0)
        End If
    With ThisDrawing.Utility
        varP7 = .PolarPoint(varP3, PI + Ang1, Dist4 / 2)
        varP8 = .PolarPoint(varP3, 0 + Ang1, Dist4 / 2)
        varP9 = .PolarPoint(varP4, PI + Ang1, Dist4 / 2)
        varP10 = .PolarPoint(varP4, 0 + Ang1, Dist4 / 2)
        varP11 = .PolarPoint(varP7, PI / -2 + Ang1, Dist5 / 2 - Dist2 / 2)
        varP12 = .PolarPoint(varP8, PI / -2 + Ang1, Dist5 / 2 - Dist2 / 2)
        varP13 = .PolarPoint(varP9, PI / 2 + Ang1, Dist5 / 2 - Dist2 / 2)
        varP14 = .PolarPoint(varP10, PI / 2 + Ang1, Dist5 / 2 - Dist2 / 2)
        varP15 = .PolarPoint(varP11, PI + Ang1, 40)
        varP16 = .PolarPoint(varP11, PI / -2 + Ang1, 40)
    End With
    arrayCor(0) = varP11(0)
    arrayCor(1) = varP11(1)
    arrayCor(2) = varP12(0)
    arrayCor(3) = varP12(1)
    arrayCor(4) = varP14(0)
    arrayCor(5) = varP14(1)
    arrayCor(6) = varP13(0)
    arrayCor(7) = varP13(1)
    Set objAddLightWeightPolyline = ThisDrawing.ModelSpace.AddLightWeightPolyline(arrayCor)
    objAddLightWeightPolyline.Closed = True
    objAddLightWeightPolyline.Layer = "C1"
    objAddLightWeightPolyline.Update
    If Me.chkRC = False Then
        Set objText1 = ThisDrawing.ModelSpace.AddText(strID + CStr(intNum) + strN, varP16, 40)
        objText1.Layer = "COLT"
        objText1.ScaleFactor = 0.7
        objText1.StyleName = "C40"
        objText1.Alignment = acAlignmentTopRight
        objText1.TextAlignmentPoint = varP11
        objText1.Update
        Set objText1 = ThisDrawing.ModelSpace.AddText("(" + CStr(Dist4) + "x" + CStr(Dist5) + ")", varP16, 40)
        objText1.Layer = "COLS"
        objText1.ScaleFactor = 0.7
        objText1.StyleName = "C40"
        objText1.Alignment = acAlignmentTopLeft
        objText1.TextAlignmentPoint = varP11
        objText1.Update
            intNum = intNum + 1
            txtNum = intNum
            intRCNum = intRCNum + 1
            txtRCNum = intRCNum
    Else
        With ThisDrawing.Utility
            varP1 = .PolarPoint(varP11, PI + Ang1, 15)
            varP2 = .PolarPoint(varP12, 0 + Ang1, 15)
            varP3 = .PolarPoint(varP13, PI + Ang1, 15)
            varP4 = .PolarPoint(varP14, 0 + Ang1, 15)
            varP5 = .PolarPoint(varP1, PI / -2 + Ang1, 15)
            varP6 = .PolarPoint(varP2, PI / -2 + Ang1, 15)
            varP7 = .PolarPoint(varP3, PI / 2 + Ang1, 15)
            varP8 = .PolarPoint(varP4, PI / 2 + Ang1, 15)
            varP10 = .PolarPoint(varP1, PI / -2, 40)
            varP11 = .PolarPoint(varP1, PI / -2, 100)
            v7a = .PolarPoint(varP10, PI + Ang1, 40)
            v8a = .PolarPoint(varP11, PI + Ang1, 40)
        End With
        arrayCor(0) = varP5(0)
        arrayCor(1) = varP5(1)
        arrayCor(2) = varP6(0)
        arrayCor(3) = varP6(1)
        arrayCor(4) = varP8(0)
        arrayCor(5) = varP8(1)
        arrayCor(6) = varP7(0)
        arrayCor(7) = varP7(1)
        Set objAddLightWeightPolyline = ThisDrawing.ModelSpace.AddLightWeightPolyline(arrayCor)
            objAddLightWeightPolyline.Closed = True
            objAddLightWeightPolyline.Layer = "C1"
            objAddLightWeightPolyline.Update
            Set objText1 = ThisDrawing.ModelSpace.AddText(strID + CStr(intNum) + strN, varP10, 40)
            objText1.Layer = "COLT"
            objText1.ScaleFactor = 0.7
            objText1.StyleName = "C40"
            objText1.Alignment = acAlignmentTopRight
            objText1.TextAlignmentPoint = varP10
            objText1.Update
            Set objText2 = ThisDrawing.ModelSpace.AddText(strRCID + CStr(intRCNum) + strRCN, varP11, 40)
            objText2.Layer = "COLT"
            objText2.ScaleFactor = 0.7
            objText2.StyleName = "C40"
            objText2.Alignment = acAlignmentTopRight
            objText2.TextAlignmentPoint = varP11
            objText2.Update
            Set objText1 = ThisDrawing.ModelSpace.AddText("(" + CStr(Dist4) + "x" + CStr(Dist5) + ")", varP10, 40)
            objText1.Layer = "COLS"
            objText1.ScaleFactor = 0.7
            objText1.StyleName = "C40"
            objText1.Alignment = acAlignmentTopLeft
            objText1.TextAlignmentPoint = varP10
            objText1.Update
            If intRCNum < 10 Then
                varP16 = ThisDrawing.Utility.PolarPoint(v8a, 0, 30)
            ElseIf intRCNum < 100 Then
                varP16 = ThisDrawing.Utility.PolarPoint(v8a, 0, 40)
            Else
                varP16 = ThisDrawing.Utility.PolarPoint(v8a, 0, 50)
            End If
            Set objText2 = ThisDrawing.ModelSpace.AddText("(" + CStr(Dist4 + 30) + "x" + CStr(Dist5 + 30) + ")", varP11, 40)
            objText2.Layer = "COLS"
            objText2.ScaleFactor = 0.7
            objText2.StyleName = "C40"
            objText2.Alignment = acAlignmentTopLeft
            objText2.TextAlignmentPoint = varP11
            objText2.Update
            intNum = intNum + 1
            txtNum = intNum
            intRCNum = intRCNum + 1
            txtRCNum = intRCNum
    End If
    Loop
Else
Do While Err.Number = 0
        On Error GoTo Z
        With ThisDrawing.Utility
            varP0 = .GetPoint(, "P1")
            varP1 = .GetPoint(varP0, "Rotate Angle")
            varP2 = .GetPoint(varP1, "P2")
            Dist1 = GetDistance(varP0, varP1)
            Dist2 = GetDistance(varP1, varP2)
            Ang1 = .AngleFromXAxis(varP0, varP1)
            varP3 = .PolarPoint(varP0, Ang1, Dist1 / 2)
            varP4 = .PolarPoint(varP3, PI / 2 + Ang1, Dist2)
            varP5 = .PolarPoint(varP1, PI / 2 + Ang1, Dist2)
            varP6 = .PolarPoint(varP0, PI / 2 + Ang1, Dist2)
        End With
        adblCoordinate(0) = varP0(0):        adblCoordinate(1) = varP0(1)
        adblCoordinate(2) = varP1(0):        adblCoordinate(3) = varP1(1)
        adblCoordinate(4) = varP3(0):        adblCoordinate(5) = varP3(1)
        adblCoordinate(6) = varP4(0):        adblCoordinate(7) = varP4(1)
        adblCoordinate(8) = varP5(0):        adblCoordinate(9) = varP5(1)
        adblCoordinate(10) = varP6(0):        adblCoordinate(11) = varP6(1)
        Set objAddLightWeightPolyline = ThisDrawing.ModelSpace.AddLightWeightPolyline(adblCoordinate)
        objAddLightWeightPolyline.Closed = False
        objAddLightWeightPolyline.Layer = "SC1"
        objAddLightWeightPolyline.Update
        If Dist1 Mod 5# <> 0 Then
            Dist4 = (Dist1 \ 5 + 1) * 5
        Else
            Dist4 = Round(Dist1, 0)
        End If
        If Dist2 Mod 5# <> 0 Then
            Dist5 = (Dist2 \ 5 + 1) * 5
        Else
            Dist5 = Round(Dist2, 0)
        End If
    With ThisDrawing.Utility
        varP7 = .PolarPoint(varP3, PI + Ang1, Dist4 / 2)
        varP8 = .PolarPoint(varP3, 0 + Ang1, Dist4 / 2)
        varP9 = .PolarPoint(varP4, PI + Ang1, Dist4 / 2)
        varP10 = .PolarPoint(varP4, 0 + Ang1, Dist4 / 2)
        varP11 = .PolarPoint(varP7, PI / -2 + Ang1, Dist5 / 2 - Dist2 / 2)
        varP12 = .PolarPoint(varP8, PI / -2 + Ang1, Dist5 / 2 - Dist2 / 2)
        varP13 = .PolarPoint(varP9, PI / 2 + Ang1, Dist5 / 2 - Dist2 / 2)
        varP14 = .PolarPoint(varP10, PI / 2 + Ang1, Dist5 / 2 - Dist2 / 2)
        varP15 = .PolarPoint(varP11, PI + Ang1, 40)
        varP16 = .PolarPoint(varP11, PI / -2 + Ang1, 40)
    End With
    arrayCor(0) = varP11(0)
    arrayCor(1) = varP11(1)
    arrayCor(2) = varP12(0)
    arrayCor(3) = varP12(1)
    arrayCor(4) = varP14(0)
    arrayCor(5) = varP14(1)
    arrayCor(6) = varP13(0)
    arrayCor(7) = varP13(1)
    Set objAddLightWeightPolyline = ThisDrawing.ModelSpace.AddLightWeightPolyline(arrayCor)
    objAddLightWeightPolyline.Closed = True
    objAddLightWeightPolyline.Layer = "C1"
    objAddLightWeightPolyline.Update
    If Me.chkRC = False Then
        Set objText1 = ThisDrawing.ModelSpace.AddText(strID + CStr(intNum) + strN, varP16, 40)
        objText1.Layer = "COLT"
        objText1.ScaleFactor = 0.7
        objText1.StyleName = "C40"
        objText1.Alignment = acAlignmentTopRight
        objText1.TextAlignmentPoint = varP11
        objText1.Update
        Set objText1 = ThisDrawing.ModelSpace.AddText("(" + CStr(Dist4) + "x" + CStr(Dist5) + ")", varP16, 40)
        objText1.Layer = "COLS"
        objText1.ScaleFactor = 0.7
        objText1.StyleName = "C40"
        objText1.Alignment = acAlignmentTopLeft
        objText1.TextAlignmentPoint = varP11
        objText1.Update
    Else
        With ThisDrawing.Utility
            varP1 = .PolarPoint(varP11, PI + Ang1, 15)
            varP2 = .PolarPoint(varP12, 0 + Ang1, 15)
            varP3 = .PolarPoint(varP13, PI + Ang1, 15)
            varP4 = .PolarPoint(varP14, 0 + Ang1, 15)
            varP5 = .PolarPoint(varP1, PI / -2 + Ang1, 15)
            varP6 = .PolarPoint(varP2, PI / -2 + Ang1, 15)
            varP7 = .PolarPoint(varP3, PI / 2 + Ang1, 15)
            varP8 = .PolarPoint(varP4, PI / 2 + Ang1, 15)
            varP10 = .PolarPoint(varP1, PI / -2, 40)
            varP11 = .PolarPoint(varP1, PI / -2, 100)
            v7a = .PolarPoint(varP10, PI + Ang1, 40)
            v8a = .PolarPoint(varP11, PI + Ang1, 40)
        End With
        arrayCor(0) = varP5(0)
        arrayCor(1) = varP5(1)
        arrayCor(2) = varP6(0)
        arrayCor(3) = varP6(1)
        arrayCor(4) = varP8(0)
        arrayCor(5) = varP8(1)
        arrayCor(6) = varP7(0)
        arrayCor(7) = varP7(1)
        Set objAddLightWeightPolyline = ThisDrawing.ModelSpace.AddLightWeightPolyline(arrayCor)
            objAddLightWeightPolyline.Closed = True
            objAddLightWeightPolyline.Layer = "C1"
            objAddLightWeightPolyline.Update
            Set objText1 = ThisDrawing.ModelSpace.AddText(strID + CStr(intNum) + strN, varP10, 40)
            objText1.Layer = "COLT"
            objText1.ScaleFactor = 0.7
            objText1.StyleName = "C40"
            objText1.Alignment = acAlignmentTopRight
            objText1.TextAlignmentPoint = varP10
            objText1.Update
            Set objText2 = ThisDrawing.ModelSpace.AddText(strRCID + CStr(intRCNum) + strRCN, varP11, 40)
            objText2.Layer = "COLT"
            objText2.ScaleFactor = 0.7
            objText2.StyleName = "C40"
            objText2.Alignment = acAlignmentTopRight
            objText2.TextAlignmentPoint = varP11
            objText2.Update
            Set objText1 = ThisDrawing.ModelSpace.AddText("(" + CStr(Dist4) + "x" + CStr(Dist5) + ")", varP10, 40)
            objText1.Layer = "COLS"
            objText1.ScaleFactor = 0.7
            objText1.StyleName = "C40"
            objText1.Alignment = acAlignmentTopLeft
            objText1.TextAlignmentPoint = varP10
            objText1.Update
            If intRCNum < 10 Then
                varP16 = ThisDrawing.Utility.PolarPoint(v8a, 0, 30)
            ElseIf intRCNum < 100 Then
                varP16 = ThisDrawing.Utility.PolarPoint(v8a, 0, 40)
            Else
                varP16 = ThisDrawing.Utility.PolarPoint(v8a, 0, 50)
            End If
            Set objText2 = ThisDrawing.ModelSpace.AddText("(" + CStr(Dist4 + 30) + "x" + CStr(Dist5 + 30) + ")", varP11, 40)
            objText2.Layer = "COLS"
            objText2.ScaleFactor = 0.7
            objText2.StyleName = "C40"
            objText2.Alignment = acAlignmentTopLeft
            objText2.TextAlignmentPoint = varP11
            objText2.Update
    End If
    Loop
End If
Z:
    Me.show
End Sub

Attribute VB_Name = "TextFunction"
'>>>>>>>>>>>>>>>>>>>>>>>>>>>>>>>>>>>>>>>>>>>>>>>>>>>>>>>>>>>>>>>>>>>>
'函數: IsExistTextStyle()
'描述: 檢查 Font 名稱是否存在
'輸入: 所需檢查的現型名稱  IsExistTextStyle
'輸出: 若存在傳回 True,不存在傳回 False
'
Public Function IsExistTextStyle(TextStyleName As String) As Boolean

    '若有錯誤發生時,將繼續執行下一行程式
    On Error Resume Next
    
    Dim objTextStyle As AcadTextStyle      '宣告為 AcadLayer物件
    
    '取得所需的字型物件
    Set objTextStyle = ThisDrawing.TextStyles.Item(TextStyleName)
    
    '若此圖層不存在則Err物件之Err.Number值將不為零
    '反之 Err.Number 值為零
    If Err.Number <> 0 Then
        '> 若物件不存在則傳回False
        IsExistTextStyle = False
    Else
        '> 若物件存在則傳回True
        IsExistTextStyle = True
    End If
    
End Function


Public Function CreateTextStyle(TextStyleName As String, FontFile As String, BigFontFile As String) As AcadTextStyle
    Dim objTextStyle As AcadTextStyle
    
    On Error GoTo HandleError
    
    '檢查字型檔是否存在
    If IsExistTextStyle(TextStyleName) Then
        '取得所需的字型物件
        Set objTextStyle = ThisDrawing.TextStyles.Item(TextStyleName)
    Else
        Set objTextStyle = ThisDrawing.TextStyles.Add(TextStyleName)
        
        '若存在但不為 .SHX 檔案名稱者
        If UCase(Right(FontFile, 4)) <> ".SHX" Then
            Call objTextStyle.SetFont(FontFile, False, False, 1, 0)
        Else
            '設定字型檔及大寫字型檔
            objTextStyle.FontFile = FontFile
            objTextStyle.BigFontFile = BigFontFile
        End If
    End If
    
    Set CreateTextStyle = objTextStyle
    Exit Function
HandleError:
    MsgBox (Err.Description)
    Set CreateTextStyle = Nothing
End Function

Attribute VB_Name = "ThisDrawing"
Attribute VB_Base = "0{74D0CE91-F931-4FAC-BEA9-EE32E43EAD37}"
Attribute VB_GlobalNameSpace = False
Attribute VB_Creatable = False
Attribute VB_PredeclaredId = True
Attribute VB_Exposed = True
Attribute VB_TemplateDerived = False
Attribute VB_Customizable = True
Private Sub AcadDocument_BeginSave(ByVal FileName As String)

End Sub

Attribute VB_Name = "modDrawing"
Sub RCSS()
    Call CreateTextStyle("C40", "c2.shx", "china.shx")
    BasicForm.show
End Sub
